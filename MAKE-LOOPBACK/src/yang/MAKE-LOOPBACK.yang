module MAKE-LOOPBACK {

  namespace "http://example.com/MAKE-LOOPBACK";
  prefix MAKE-LOOPBACK;

  import ietf-inet-types {
    prefix inet;
  }
  import tailf-common {
    prefix tailf;
  }
  import tailf-ncs {
    prefix ncs;
  }
  revision 2016-01-01 {
    description
      "Initial revision.";
  }
  list MAKE-LOOPBACK {
    description "This is an RFS skeleton service";
    key name;
    leaf name {
      tailf:info "Unique service id";
      tailf:cli-allow-range;
      type string;
    }
    uses ncs:service-data;
    ncs:servicepoint MAKE-LOOPBACK-servicepoint;
    // may replace this with other ways of refering to the devices.
    // replace with your own stuff here
    leaf hostname {
      type string;
    }
  }
}
