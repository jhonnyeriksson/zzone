module cisco-ios-cli-6.107 {
  yang-version 1.1;
  namespace "http://tail-f.com/ns/ned-id/cisco-ios-cli-6.107";
  prefix cisco-ios-cli-6.107;

  import cisco-ios-cli {
    prefix family;
  }

  identity cisco-ios-cli-6.107 {
    base family:cisco-ios-cli;
  }
}
