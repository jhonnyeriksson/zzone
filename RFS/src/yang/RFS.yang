module RFS {

  namespace "http://example.com/RFS";
  prefix RFS;

  import tailf-common {
    prefix tailf;
  }
  import tailf-ncs {
    prefix ncs;
  }

  description
    "Resource-facing service: create loopbacks on a device.";

  revision 2016-01-01 {
    description
      "Initial revision.";
  }

  list RFS {
    description "RFS that creates device loopbacks from hostname";

    key name;
    leaf name {
      tailf:info "Unique service id";
      tailf:cli-allow-range;
      type string;
    }

    uses ncs:service-data;
    ncs:servicepoint RFS-servicepoint;

    leaf hostname {
      tailf:info "Device hostname";
      mandatory true;
      type leafref {
        path "/ncs:devices/ncs:device/ncs:name";
      }
    }
  }
}
