module extreme-xos-cli-1.5 {
  yang-version 1.1;
  namespace "http://tail-f.com/ns/ned-id/extreme-xos-cli-1.5";
  prefix extreme-xos-cli-1.5;

  import extreme-xos-cli {
    prefix family;
  }

  identity extreme-xos-cli-1.5 {
    base family:extreme-xos-cli;
  }
}
