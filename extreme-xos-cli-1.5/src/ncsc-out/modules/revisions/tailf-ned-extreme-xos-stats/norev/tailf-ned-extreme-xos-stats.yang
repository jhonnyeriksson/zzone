module tailf-ned-extreme-xos-stats {
  // Generated by yanger -t ncs
  tailf:mount-id "extreme-xos-cli-1.5:extreme-xos-cli-1.5";
  tailf:ncs-device-type "cli-ned";

  namespace "http://tail-f.com/ned/extreme-xos/stats";
  prefix extreme-xos-stats;

  import tailf-common {
    prefix tailf;
  }
  import tailf-ncs {
    prefix ncs;
  }

  augment "/ncs:devices/ncs:device/ncs:live-status" {
    container exec {
      tailf:ncs-device-type "cli-ned";
      tailf:display-when "not(../../ncs:module) or ../../ncs:module[ncs:name='tailf-ned-extreme-xos-stats'] or (../../ncs:live-status-protocol[not(ncs:capability)]) or (../../ncs:live-status-protocol/ncs:capability/ncs:module[.='tailf-ned-extreme-xos-stats'])";
      tailf:info
        "Execute commands on device";
      tailf:action any {
        tailf:actionpoint ncsproxy {
          tailf:internal;
        }
        tailf:info
          "Run any command on the device";
        // NCS drop tailf:actionpoint
        input {
          leaf-list args {
            tailf:cli-drop-node-name;
            tailf:cli-flat-list-syntax;
            type string {
              tailf:info
                "Commands to be run";
            }
          }
        }
        output {
          leaf result {
            type string;
          }
        }
      }
      tailf:action scp2 {
        tailf:actionpoint ncsproxy {
          tailf:internal;
        }
        tailf:info
          "Run scp2 command";
        // NCS drop tailf:actionpoint
        input {
          leaf vr {
            tailf:info
              "Virtual router";
            type string {
              tailf:info
                "<vr_name>;;Virtual router name, default VR-Mgmt";
            }
          }
          leaf host {
            type string {
              tailf:info
                "<user@host:file>;;User @ remote host or IP address
                 (IPv6 addresses in square brackets) with remote file name";
            }
          }
          leaf local-file {
            type string {
              tailf:info
                "<local-file>;;Local file name";
            }
          }
          leaf password {
            tailf:suppress-echo true;
            type tailf:aes-cfb-128-encrypted-string {
              tailf:info
                "Password";
            }
          }
        }
        output {
          leaf result {
            type string;
          }
        }
      }
    }
  }
}
