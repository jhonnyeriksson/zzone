module tailf-ned-extreme-xos-id {
  // Generated by yanger -t ncs
  tailf:mount-id "extreme-xos-cli-1.5:extreme-xos-cli-1.5";
  tailf:ncs-device-type "cli-ned";

  namespace "http://tail-f.com/ned/extreme-xos-id";
  prefix extreme-xos-id;

  import tailf-ncs-ned {
    prefix ned;
  }
  import tailf-common {
    prefix tailf;
  }
  import tailf-ncs {
    prefix ncs;
  }

  identity extreme-xos {
    base ned:cli-ned-id;
  }
}
