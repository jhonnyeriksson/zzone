module tailf-ned-extreme-xos {
  // Generated by yanger -t ncs
  tailf:mount-id "extreme-xos-cli-1.5:extreme-xos-cli-1.5";
  tailf:ncs-device-type "cli-ned";

  namespace "http://tail-f.com/ned/extreme-xos";
  prefix extreme-xos;

  import tailf-common {
    prefix tailf;
  }
  import ietf-inet-types {
    prefix inet;
  }
  import cliparser-extensions-v11 {
    prefix cli;
  }
  import ietf-yang-types {
    prefix yang;
  }
  import tailf-ncs {
    prefix ncs;
  }

  revision 2024-05-10 {
    description
      "version 1.5.4, see CHANGES";
  }

  grouping ncs_compliance_template_port-list-grouping {
    list ports {
      // NCS patched for predictable order
      ordered-by user;
      // NCS drop tailf-common:cli-diff-set-after statement
      // NCS drop tailf-common:cli-diff-delete-before statement
      tailf:cli-suppress-mode;
      tailf:cli-range-list-syntax;
      key "id";
      leaf id {
        type string;
      }
    }
  }

  grouping ncs_compliance_template_ports-enable-grouping {
    list ports {
      // NCS patched for predictable order
      ordered-by user;
      extreme-xos:replace-delete-output "un(configure.*)ena(ble.*) :: $1disa$2";
      tailf:cli-drop-node-name;
      // NCS drop tailf-common:cli-diff-set-after statement
      // NCS drop tailf-common:cli-diff-delete-before statement
      // NCS drop tailf-common:cli-diff-create-after statement
      // NCS drop tailf-common:cli-diff-delete-before statement
      // NCS drop tailf-common:cli-diff-create-after statement
      // NCS drop tailf-common:cli-diff-delete-before statement
      // NCS drop tailf-common:cli-diff-create-after statement
      // NCS drop tailf-common:cli-diff-create-after statement
      // NCS drop tailf-common:cli-diff-delete-before statement
      // NCS drop tailf-common:cli-diff-delete-before statement
      tailf:cli-suppress-mode;
      tailf:cli-range-list-syntax;
      key "id";
      leaf id {
        type string;
      }
      leaf enable {
        type empty;
      }
    }
  }

  grouping ncs_compliance_template_vlanList-grouping {
    leaf-list vlan {
      // NCS patched for predictable order
      ordered-by user;
      // NCS drop tailf-common:cli-diff-set-after statement
      // NCS drop tailf-common:cli-diff-delete-before statement
      type string;
    }
  }

  grouping ncs_compliance_template_netlogin-authprotocol-grouping {
    leaf dot1x {
      type empty;
    }
    leaf mac {
      type empty;
    }
    leaf web-based {
      type empty;
    }
  }

  grouping ncs_compliance_template_radius-timeout-grouping {
    leaf timeout {
      extreme-xos:replace-delete-output "unconfigure(.*) :: configure$1 3";
      type string;
      // NCS drop default statement
    }
  }

  grouping ncs_compliance_template_shared-secret-grouping {
    container shared-secret {
      leaf encrypted {
        cli:secret "encrypted <SECRET>" {
          cli:arguments "always-encrypted";
        }
        extreme-xos:send-secret;
        extreme-xos:quoted-string;
        type string;
      }
    }
  }

  grouping ncs_compliance_template_exam-grouping {
    container examination {
      container ports {
        choice ports {
          leaf all {
            type empty;
          }
          leaf-list ports-list {
            // NCS patched for predictable order
            ordered-by user;
            tailf:cli-range-list-syntax;
            tailf:cli-drop-node-name;
            type string;
          }
        }
      }
    }
  }

  grouping ncs_compliance_template_user-grouping {
    leaf user {
      type string;
    }
  }

  grouping ncs_compliance_template_sec-level-grouping {
    leaf sec-level {
      type string;
    }
  }

  grouping ncs_compliance_template_sec-model-grouping {
    leaf sec-model {
      type string;
    }
  }

  grouping ncs_compliance_template_sntpc-grouping {
    leaf host {
      tailf:cli-drop-node-name;
      type string;
    }
    leaf vr {
      // NCS drop tailf-common:cli-diff-create-after statement
      // NCS drop tailf-common:cli-diff-delete-before statement
      type string;
    }
  }

  grouping ncs_compliance_template_vr-grouping {
    leaf vr {
      // NCS drop tailf-common:cli-diff-create-after statement
      // NCS drop tailf-common:cli-diff-delete-before statement
      type string;
    }
  }

  grouping ncs_compliance_template_portList-grouping {
    leaf-list ports {
      // NCS patched for predictable order
      ordered-by user;
      tailf:cli-range-list-syntax;
      type string;
    }
  }

  grouping ncs_compliance_template_tacacs-grouping {
    container primary {
      uses ncs_compliance_template_tacacs-server-grouping;
    }
    container secondary {
      uses ncs_compliance_template_tacacs-server-grouping;
    }
    leaf timeout {
      extreme-xos:replace-delete-output "unconfigure (\\S+) timeout :: configure $1 timeout 3";
      // NCS drop tailf-common:ned-default-handling statement
      type string;
      // NCS drop default statement
    }
  }

  grouping ncs_compliance_template_tacacs-server-grouping {
    container server {
      leaf host {
        tailf:cli-drop-node-name;
        type string;
      }
      leaf port {
        tailf:cli-drop-node-name;
        type string;
      }
      leaf client-ip {
        type string;
      }
      leaf vr {
        // NCS drop tailf-common:cli-diff-create-after statement
        // NCS drop tailf-common:cli-diff-delete-before statement
        type string;
      }
    }
    uses ncs_compliance_template_shared-secret-grouping;
  }

  grouping ncs_template_port-list-grouping {
    list ports {
      // NCS patched for predictable order
      ordered-by user;
      // NCS drop tailf-common:cli-diff-set-after statement
      // NCS drop tailf-common:cli-diff-delete-before statement
      tailf:cli-suppress-mode;
      tailf:cli-range-list-syntax;
      key "id";
      leaf id {
        type string;
      }
    }
  }

  grouping ncs_template_ports-enable-grouping {
    list ports {
      // NCS patched for predictable order
      ordered-by user;
      extreme-xos:replace-delete-output "un(configure.*)ena(ble.*) :: $1disa$2";
      tailf:cli-drop-node-name;
      // NCS drop tailf-common:cli-diff-set-after statement
      // NCS drop tailf-common:cli-diff-delete-before statement
      // NCS drop tailf-common:cli-diff-create-after statement
      // NCS drop tailf-common:cli-diff-delete-before statement
      // NCS drop tailf-common:cli-diff-create-after statement
      // NCS drop tailf-common:cli-diff-delete-before statement
      // NCS drop tailf-common:cli-diff-create-after statement
      // NCS drop tailf-common:cli-diff-create-after statement
      // NCS drop tailf-common:cli-diff-delete-before statement
      // NCS drop tailf-common:cli-diff-delete-before statement
      tailf:cli-suppress-mode;
      tailf:cli-range-list-syntax;
      key "id";
      leaf id {
        type string;
      }
      leaf enable {
        type empty;
      }
    }
  }

  grouping ncs_template_vlanList-grouping {
    leaf-list vlan {
      // NCS patched for predictable order
      ordered-by user;
      // NCS drop tailf-common:cli-diff-set-after statement
      // NCS drop tailf-common:cli-diff-delete-before statement
      type string;
    }
  }

  grouping ncs_template_netlogin-authprotocol-grouping {
    leaf dot1x {
      type empty;
    }
    leaf mac {
      type empty;
    }
    leaf web-based {
      type empty;
    }
  }

  grouping ncs_template_radius-timeout-grouping {
    leaf timeout {
      extreme-xos:replace-delete-output "unconfigure(.*) :: configure$1 3";
      type string;
      // NCS drop default statement
    }
  }

  grouping ncs_template_shared-secret-grouping {
    container shared-secret {
      leaf encrypted {
        cli:secret "encrypted <SECRET>" {
          cli:arguments "always-encrypted";
        }
        extreme-xos:send-secret;
        extreme-xos:quoted-string;
        type string;
      }
    }
  }

  grouping ncs_template_exam-grouping {
    container examination {
      container ports {
        choice ports {
          leaf all {
            type empty;
          }
          leaf-list ports-list {
            // NCS patched for predictable order
            ordered-by user;
            tailf:cli-range-list-syntax;
            tailf:cli-drop-node-name;
            type string;
          }
        }
      }
    }
  }

  grouping ncs_template_user-grouping {
    leaf user {
      type string;
    }
  }

  grouping ncs_template_sec-level-grouping {
    leaf sec-level {
      type string;
    }
  }

  grouping ncs_template_sec-model-grouping {
    leaf sec-model {
      type string;
    }
  }

  grouping ncs_template_sntpc-grouping {
    leaf host {
      tailf:cli-drop-node-name;
      type string;
    }
    leaf vr {
      // NCS drop tailf-common:cli-diff-create-after statement
      // NCS drop tailf-common:cli-diff-delete-before statement
      type string;
    }
  }

  grouping ncs_template_vr-grouping {
    leaf vr {
      // NCS drop tailf-common:cli-diff-create-after statement
      // NCS drop tailf-common:cli-diff-delete-before statement
      type string;
    }
  }

  grouping ncs_template_portList-grouping {
    leaf-list ports {
      // NCS patched for predictable order
      ordered-by user;
      tailf:cli-range-list-syntax;
      type string;
    }
  }

  grouping ncs_template_tacacs-grouping {
    container primary {
      uses ncs_template_tacacs-server-grouping;
    }
    container secondary {
      uses ncs_template_tacacs-server-grouping;
    }
    leaf timeout {
      extreme-xos:replace-delete-output "unconfigure (\\S+) timeout :: configure $1 timeout 3";
      // NCS drop tailf-common:ned-default-handling statement
      type string;
      // NCS drop default statement
    }
  }

  grouping ncs_template_tacacs-server-grouping {
    container server {
      leaf host {
        tailf:cli-drop-node-name;
        type string;
      }
      leaf port {
        tailf:cli-drop-node-name;
        type string;
      }
      leaf client-ip {
        type string;
      }
      leaf vr {
        // NCS drop tailf-common:cli-diff-create-after statement
        // NCS drop tailf-common:cli-diff-delete-before statement
        type string;
      }
    }
    uses ncs_template_shared-secret-grouping;
  }

  grouping ncs_rpc_notif_port-list-grouping {
    list ports {
      tailf:cli-diff-set-after "/extreme-xos:create/vlan" {
        tailf:xpath-root 3;
        tailf:cli-when-target-create;
      }
      tailf:cli-diff-delete-before "/extreme-xos:create/vlan" {
        tailf:xpath-root 3;
        tailf:cli-when-target-delete;
      }
      tailf:info
        "Ports";
      tailf:cli-suppress-mode;
      tailf:cli-compact-syntax;
      tailf:cli-range-list-syntax;
      key "id";
      leaf id {
        type union {
          type uint32 {
            tailf:info
              "<port_list>;;Port list";
          }
          type enumeration {
            enum "all" {
              tailf:info
                "all";
            }
          }
        }
      }
    }
  }

  grouping ncs_rpc_notif_ports-enable-grouping {
    list ports {
      extreme-xos:replace-delete-output "un(configure.*)ena(ble.*) :: $1disa$2";
      tailf:cli-drop-node-name;
      tailf:cli-diff-set-after "/extreme-xos:create/vlan" {
        tailf:xpath-root 3;
        tailf:cli-when-target-create;
      }
      tailf:cli-diff-delete-before "/extreme-xos:create/vlan" {
        tailf:xpath-root 3;
        tailf:cli-when-target-delete;
      }
      tailf:cli-diff-create-after "/extreme-xos:enable/stpd" {
        tailf:xpath-root 3;
        tailf:cli-when-target-create;
      }
      tailf:cli-diff-delete-before "/extreme-xos:enable/stpd" {
        tailf:xpath-root 3;
        tailf:cli-when-target-delete;
      }
      tailf:cli-diff-create-after "/extreme-xos:create/stpd" {
        tailf:xpath-root 3;
        tailf:cli-when-target-create;
      }
      tailf:cli-diff-delete-before "/extreme-xos:create/stpd" {
        tailf:xpath-root 3;
        tailf:cli-when-target-delete;
      }
      tailf:cli-diff-create-after "/extreme-xos:enable/stpd/auto-bind/vlan" {
        tailf:xpath-root 3;
        tailf:cli-when-target-set;
      }
      tailf:cli-diff-create-after "/extreme-xos:enable/stpd/auto-bind/vlan" {
        tailf:xpath-root 3;
        tailf:cli-when-target-modify;
      }
      tailf:cli-diff-delete-before "/extreme-xos:enable/stpd/auto-bind/vlan" {
        tailf:xpath-root 3;
        tailf:cli-when-target-delete;
      }
      tailf:cli-diff-delete-before "/extreme-xos:enable/stpd/auto-bind/vlan" {
        tailf:xpath-root 3;
        tailf:cli-when-target-modify;
      }
      tailf:cli-suppress-mode;
      tailf:cli-delete-when-empty;
      tailf:cli-range-list-syntax;
      key "id";
      leaf id {
        type union {
          type uint32 {
            tailf:info
              "<port_list>;;Port list";
          }
          type enumeration {
            enum "all" {
              tailf:info
                "all";
            }
          }
        }
      }
      leaf enable {
        tailf:cli-prefix-key;
        tailf:info
          "Enable option";
        type empty;
      }
    }
  }

  grouping ncs_rpc_notif_vlanList-grouping {
    leaf-list vlan {
      tailf:cli-list-syntax;
      // NCS drop tailf-common:non-strict-leafref statement
      tailf:cli-diff-set-after "/extreme-xos:create/vlan" {
        tailf:xpath-root 3;
        tailf:cli-when-target-create;
      }
      tailf:cli-diff-delete-before "/extreme-xos:create/vlan" {
        tailf:xpath-root 3;
        tailf:cli-when-target-delete;
      }
      tailf:info
        "VLAN";
      type string {
        tailf:info
          "<vlan_name>;;VLAN name";
      }
    }
  }

  grouping ncs_rpc_notif_netlogin-authprotocol-grouping {
    leaf dot1x {
      tailf:info
        "Configure the 802.1x authentication protocol";
      type empty;
    }
    leaf mac {
      tailf:info
        "Configure the MAC-based authentication protocol";
      type empty;
    }
    leaf web-based {
      tailf:info
        "Configure the web-based authentication protocol";
      type empty;
    }
  }

  grouping ncs_rpc_notif_radius-timeout-grouping {
    leaf timeout {
      extreme-xos:replace-delete-output "unconfigure(.*) :: configure$1 3";
      tailf:cli-no-value-on-delete;
      tailf:info
        "RADIUS server timeout";
      type uint16 {
        tailf:info
          "<seconds>;;RADIUS server timeout seconds. Range is 1 to 240.";
      }
      default "3";
    }
  }

  grouping ncs_rpc_notif_shared-secret-grouping {
    container shared-secret {
      tailf:info
        "shared secret";
      tailf:cli-flatten-container;
      leaf encrypted {
        cli:secret "encrypted <SECRET>" {
          cli:arguments "always-encrypted";
        }
        extreme-xos:send-secret;
        extreme-xos:quoted-string;
        tailf:info
          "Password is Encrypted";
        type string {
          tailf:info
            "<encrypted_secret>;;encrypted secret string";
        }
      }
    }
  }

  grouping ncs_rpc_notif_exam-grouping {
    container examination {
      tailf:info
        "examination";
      container ports {
        tailf:info
          "ports";
        choice ports {
          leaf all {
            tailf:info
              "all";
            type empty;
          }
          leaf-list ports-list {
            tailf:cli-list-syntax;
            tailf:cli-range-list-syntax;
            tailf:cli-drop-node-name;
            type uint32 {
              tailf:info
                "<port_list>;;Port list";
            }
          }
        }
      }
    }
  }

  grouping ncs_rpc_notif_user-grouping {
    leaf user {
      tailf:cli-suppress-no;
      tailf:cli-no-value-on-delete;
      tailf:cli-no-name-on-delete;
      tailf:info
        "User";
      type string {
        tailf:info
          "hex|<user_name>;;Following value is to be specified in hexadecimal
                  User Name (in ASCII)";
      }
    }
  }

  grouping ncs_rpc_notif_sec-level-grouping {
    leaf sec-level {
      tailf:info
        "Security Level";
      type enumeration {
        enum "authnopriv";
        enum "noauth";
        enum "priv";
      }
    }
  }

  grouping ncs_rpc_notif_sec-model-grouping {
    leaf sec-model {
      tailf:info
        "Security Model";
      type enumeration {
        enum "snmpv1";
        enum "snmpv2c";
        enum "usm";
      }
    }
  }

  grouping ncs_rpc_notif_sntpc-grouping {
    leaf host {
      tailf:cli-no-value-on-delete;
      tailf:cli-drop-node-name;
      type inet:host;
    }
    leaf vr {
      tailf:cli-diff-create-after "/extreme-xos:create/vr" {
        tailf:xpath-root 3;
        tailf:cli-when-target-create;
      }
      tailf:cli-diff-delete-before "/extreme-xos:create/vr" {
        tailf:xpath-root 3;
        tailf:cli-when-target-delete;
      }
      tailf:cli-no-value-on-delete;
      tailf:cli-no-name-on-delete;
      tailf:info
        "Virtual router ID";
      type string {
        tailf:info
          "<vr_name>;;Virtual router ID";
      }
    }
  }

  grouping ncs_rpc_notif_vr-grouping {
    leaf vr {
      tailf:cli-diff-create-after "/extreme-xos:create/vr" {
        tailf:xpath-root 3;
        tailf:cli-when-target-create;
      }
      tailf:cli-diff-delete-before "/extreme-xos:create/vr" {
        tailf:xpath-root 3;
        tailf:cli-when-target-delete;
      }
      tailf:info
        "Virtual router ID";
      type string {
        tailf:info
          "<vr_name>;;Virtual router ID";
      }
    }
  }

  grouping ncs_rpc_notif_portList-grouping {
    leaf-list ports {
      tailf:info
        "Physical ports";
      tailf:cli-range-list-syntax;
      type uint32 {
        tailf:info
          "<portlist>;;List of ports separated by comma";
      }
    }
  }

  grouping ncs_rpc_notif_tacacs-grouping {
    container primary {
      tailf:info
        "primary server";
      uses ncs_rpc_notif_tacacs-server-grouping;
    }
    container secondary {
      tailf:info
        "secondary server";
      uses ncs_rpc_notif_tacacs-server-grouping;
    }
    leaf timeout {
      extreme-xos:replace-delete-output "unconfigure (\\S+) timeout :: configure $1 timeout 3";
      tailf:ned-default-handling trim;
      tailf:cli-no-value-on-delete;
      tailf:info
        "TACACS+ server timeout";
      type uint32 {
        tailf:info
          "<sec>;;TACACS+ server timeout seconds";
      }
      default "3";
    }
  }

  grouping ncs_rpc_notif_tacacs-server-grouping {
    container server {
      tailf:info
        "TACACS+ server";
      tailf:cli-compact-syntax;
      tailf:cli-sequence-commands;
      leaf host {
        tailf:cli-no-value-on-delete;
        tailf:cli-drop-node-name;
        type inet:host;
      }
      leaf port {
        tailf:cli-no-value-on-delete;
        tailf:cli-drop-node-name;
        type uint32 {
          tailf:info
            "<tcp_port>;;server tcp port";
        }
      }
      leaf client-ip {
        tailf:cli-no-value-on-delete;
        tailf:cli-no-name-on-delete;
        tailf:info
          "client ip";
        type inet:ip-address {
          tailf:info
            "<client_ipaddr>;;client ip ipaddress";
        }
      }
      leaf vr {
        tailf:cli-no-value-on-delete;
        tailf:cli-no-name-on-delete;
        tailf:cli-diff-create-after "/extreme-xos:create/vr" {
          tailf:xpath-root 3;
          tailf:cli-when-target-create;
        }
        tailf:cli-diff-delete-before "/extreme-xos:create/vr" {
          tailf:xpath-root 3;
          tailf:cli-when-target-delete;
        }
        tailf:info
          "Virtual router ID";
        type string {
          tailf:info
            "<vr_name>;;Virtual router ID";
        }
      }
    }
    uses ncs_rpc_notif_shared-secret-grouping;
  }

  grouping port-list-grouping {
    list ports {
      tailf:cli-diff-set-after "/extreme-xos:create/vlan" {
        tailf:xpath-root 3;
        tailf:cli-when-target-create;
      }
      tailf:cli-diff-delete-before "/extreme-xos:create/vlan" {
        tailf:xpath-root 3;
        tailf:cli-when-target-delete;
      }
      tailf:info
        "Ports";
      tailf:cli-suppress-mode;
      tailf:cli-compact-syntax;
      tailf:cli-range-list-syntax;
      key "id";
      leaf id {
        type union {
          type uint32 {
            tailf:info
              "<port_list>;;Port list";
          }
          type enumeration {
            enum "all" {
              tailf:info
                "all";
            }
          }
        }
      }
    }
  }

  grouping ports-enable-grouping {
    list ports {
      extreme-xos:replace-delete-output "un(configure.*)ena(ble.*) :: $1disa$2";
      tailf:cli-drop-node-name;
      tailf:cli-diff-set-after "/extreme-xos:create/vlan" {
        tailf:xpath-root 3;
        tailf:cli-when-target-create;
      }
      tailf:cli-diff-delete-before "/extreme-xos:create/vlan" {
        tailf:xpath-root 3;
        tailf:cli-when-target-delete;
      }
      tailf:cli-diff-create-after "/extreme-xos:enable/stpd" {
        tailf:xpath-root 3;
        tailf:cli-when-target-create;
      }
      tailf:cli-diff-delete-before "/extreme-xos:enable/stpd" {
        tailf:xpath-root 3;
        tailf:cli-when-target-delete;
      }
      tailf:cli-diff-create-after "/extreme-xos:create/stpd" {
        tailf:xpath-root 3;
        tailf:cli-when-target-create;
      }
      tailf:cli-diff-delete-before "/extreme-xos:create/stpd" {
        tailf:xpath-root 3;
        tailf:cli-when-target-delete;
      }
      tailf:cli-diff-create-after "/extreme-xos:enable/stpd/auto-bind/vlan" {
        tailf:xpath-root 3;
        tailf:cli-when-target-set;
      }
      tailf:cli-diff-create-after "/extreme-xos:enable/stpd/auto-bind/vlan" {
        tailf:xpath-root 3;
        tailf:cli-when-target-modify;
      }
      tailf:cli-diff-delete-before "/extreme-xos:enable/stpd/auto-bind/vlan" {
        tailf:xpath-root 3;
        tailf:cli-when-target-delete;
      }
      tailf:cli-diff-delete-before "/extreme-xos:enable/stpd/auto-bind/vlan" {
        tailf:xpath-root 3;
        tailf:cli-when-target-modify;
      }
      tailf:cli-suppress-mode;
      tailf:cli-delete-when-empty;
      tailf:cli-range-list-syntax;
      key "id";
      leaf id {
        type union {
          type uint32 {
            tailf:info
              "<port_list>;;Port list";
          }
          type enumeration {
            enum "all" {
              tailf:info
                "all";
            }
          }
        }
      }
      leaf enable {
        tailf:cli-prefix-key;
        tailf:info
          "Enable option";
        type empty;
      }
    }
  }

  grouping vlanList-grouping {
    leaf-list vlan {
      tailf:cli-list-syntax;
      tailf:non-strict-leafref {
        path "/ncs:devices/ncs:device/ncs:config/extreme-xos:create/vlan/id" {
          tailf:xpath-root 3;
        }
      }
      tailf:cli-diff-set-after "/extreme-xos:create/vlan" {
        tailf:xpath-root 3;
        tailf:cli-when-target-create;
      }
      tailf:cli-diff-delete-before "/extreme-xos:create/vlan" {
        tailf:xpath-root 3;
        tailf:cli-when-target-delete;
      }
      tailf:info
        "VLAN";
      type string {
        tailf:info
          "<vlan_name>;;VLAN name";
      }
    }
  }

  grouping netlogin-authprotocol-grouping {
    leaf dot1x {
      tailf:info
        "Configure the 802.1x authentication protocol";
      type empty;
    }
    leaf mac {
      tailf:info
        "Configure the MAC-based authentication protocol";
      type empty;
    }
    leaf web-based {
      tailf:info
        "Configure the web-based authentication protocol";
      type empty;
    }
  }

  grouping radius-timeout-grouping {
    leaf timeout {
      extreme-xos:replace-delete-output "unconfigure(.*) :: configure$1 3";
      tailf:cli-no-value-on-delete;
      tailf:info
        "RADIUS server timeout";
      type uint16 {
        tailf:info
          "<seconds>;;RADIUS server timeout seconds. Range is 1 to 240.";
      }
      default "3";
    }
  }

  grouping shared-secret-grouping {
    container shared-secret {
      tailf:info
        "shared secret";
      tailf:cli-flatten-container;
      leaf encrypted {
        cli:secret "encrypted <SECRET>" {
          cli:arguments "always-encrypted";
        }
        extreme-xos:send-secret;
        extreme-xos:quoted-string;
        tailf:info
          "Password is Encrypted";
        type string {
          tailf:info
            "<encrypted_secret>;;encrypted secret string";
        }
      }
    }
  }

  grouping exam-grouping {
    container examination {
      tailf:info
        "examination";
      container ports {
        tailf:info
          "ports";
        choice ports {
          leaf all {
            tailf:info
              "all";
            type empty;
          }
          leaf-list ports-list {
            tailf:cli-list-syntax;
            tailf:cli-range-list-syntax;
            tailf:cli-drop-node-name;
            type uint32 {
              tailf:info
                "<port_list>;;Port list";
            }
          }
        }
      }
    }
  }

  grouping user-grouping {
    leaf user {
      tailf:cli-suppress-no;
      tailf:cli-no-value-on-delete;
      tailf:cli-no-name-on-delete;
      tailf:info
        "User";
      type string {
        tailf:info
          "hex|<user_name>;;Following value is to be specified in hexadecimal
                  User Name (in ASCII)";
      }
    }
  }

  grouping sec-level-grouping {
    leaf sec-level {
      tailf:info
        "Security Level";
      type enumeration {
        enum "authnopriv";
        enum "noauth";
        enum "priv";
      }
    }
  }

  grouping sec-model-grouping {
    leaf sec-model {
      tailf:info
        "Security Model";
      type enumeration {
        enum "snmpv1";
        enum "snmpv2c";
        enum "usm";
      }
    }
  }

  grouping sntpc-grouping {
    leaf host {
      tailf:cli-no-value-on-delete;
      tailf:cli-drop-node-name;
      type inet:host;
    }
    leaf vr {
      tailf:cli-diff-create-after "/extreme-xos:create/vr" {
        tailf:xpath-root 3;
        tailf:cli-when-target-create;
      }
      tailf:cli-diff-delete-before "/extreme-xos:create/vr" {
        tailf:xpath-root 3;
        tailf:cli-when-target-delete;
      }
      tailf:cli-no-value-on-delete;
      tailf:cli-no-name-on-delete;
      tailf:info
        "Virtual router ID";
      type string {
        tailf:info
          "<vr_name>;;Virtual router ID";
      }
    }
  }

  grouping vr-grouping {
    leaf vr {
      tailf:cli-diff-create-after "/extreme-xos:create/vr" {
        tailf:xpath-root 3;
        tailf:cli-when-target-create;
      }
      tailf:cli-diff-delete-before "/extreme-xos:create/vr" {
        tailf:xpath-root 3;
        tailf:cli-when-target-delete;
      }
      tailf:info
        "Virtual router ID";
      type string {
        tailf:info
          "<vr_name>;;Virtual router ID";
      }
    }
  }

  grouping portList-grouping {
    leaf-list ports {
      tailf:info
        "Physical ports";
      tailf:cli-range-list-syntax;
      type uint32 {
        tailf:info
          "<portlist>;;List of ports separated by comma";
      }
    }
  }

  grouping tacacs-grouping {
    container primary {
      tailf:info
        "primary server";
      uses tacacs-server-grouping;
    }
    container secondary {
      tailf:info
        "secondary server";
      uses tacacs-server-grouping;
    }
    leaf timeout {
      extreme-xos:replace-delete-output "unconfigure (\\S+) timeout :: configure $1 timeout 3";
      tailf:ned-default-handling trim;
      tailf:cli-no-value-on-delete;
      tailf:info
        "TACACS+ server timeout";
      type uint32 {
        tailf:info
          "<sec>;;TACACS+ server timeout seconds";
      }
      default "3";
    }
  }

  grouping tacacs-server-grouping {
    container server {
      tailf:info
        "TACACS+ server";
      tailf:cli-compact-syntax;
      tailf:cli-sequence-commands;
      leaf host {
        tailf:cli-no-value-on-delete;
        tailf:cli-drop-node-name;
        type inet:host;
      }
      leaf port {
        tailf:cli-no-value-on-delete;
        tailf:cli-drop-node-name;
        type uint32 {
          tailf:info
            "<tcp_port>;;server tcp port";
        }
      }
      leaf client-ip {
        tailf:cli-no-value-on-delete;
        tailf:cli-no-name-on-delete;
        tailf:info
          "client ip";
        type inet:ip-address {
          tailf:info
            "<client_ipaddr>;;client ip ipaddress";
        }
      }
      leaf vr {
        tailf:cli-no-value-on-delete;
        tailf:cli-no-name-on-delete;
        tailf:cli-diff-create-after "/extreme-xos:create/vr" {
          tailf:xpath-root 3;
          tailf:cli-when-target-create;
        }
        tailf:cli-diff-delete-before "/extreme-xos:create/vr" {
          tailf:xpath-root 3;
          tailf:cli-when-target-delete;
        }
        tailf:info
          "Virtual router ID";
        type string {
          tailf:info
            "<vr_name>;;Virtual router ID";
        }
      }
    }
    uses shared-secret-grouping;
  }

  augment "/ncs:devices/ncs:device/ncs:config" {
    container create {
      tailf:ncs-device-type "cli-ned";
      tailf:display-when "not(../../ncs:module) or ../../ncs:module[ncs:name='tailf-ned-extreme-xos']";
      extreme-xos:delete-with "delete";
      tailf:info
        "Create system configuration";
      list account {
        tailf:info
          "Login account";
        tailf:cli-compact-syntax;
        tailf:cli-suppress-mode;
        key "account-name";
        leaf account-name {
          type string {
            tailf:info
              "<account-name>;;Account name";
          }
        }
        leaf account-type {
          tailf:cli-prefix-key;
          tailf:cli-no-value-on-delete;
          tailf:cli-drop-node-name;
          type enumeration {
            enum "admin" {
              tailf:info
                "Administrative privilege";
            }
            enum "lawful-intercept" {
              tailf:info
                "Lawful intercept privilege";
            }
            enum "user" {
              tailf:info
                "User (non-administrative) privilege";
            }
          }
        }
        leaf encrypted {
          tailf:cli-suppress-no;
          tailf:cli-no-value-on-delete;
          tailf:cli-no-name-on-delete;
          cli:secret "encrypted <SECRET>" {
            cli:arguments "always-encrypted";
          }
          extreme-xos:accounts-password;
          tailf:info
            "Password is Encrypted";
          type string {
            tailf:info
              "<new_password>;;clear-text or post-encrypted hash code";
          }
        }
        leaf old-password {
          type string {
            tailf:info
              "<old_password>;;clear-text old password";
          }
          tailf:cli-suppress-no;
          tailf:cli-no-value-on-delete;
          tailf:cli-no-name-on-delete;
          tailf:cli-drop-node-name;
          tailf:ned-ignore-compare-config;
        }
      }
      list access-list {
        extreme-xos:redeploy-access-profile-at-acl-modify;
        tailf:info
          "dynamic rule";
        tailf:cli-compact-syntax;
        tailf:cli-delete-when-empty;
        tailf:cli-remove-before-change;
        tailf:cli-sequence-commands {
          tailf:cli-reset-siblings;
        }
        tailf:cli-suppress-mode;
        key "dynamic-rule";
        leaf dynamic-rule {
          type string {
            tailf:info
              "<dynamic-rule>;;Dynamic Rule Name";
          }
        }
        leaf conditions {
          tailf:cli-suppress-no;
          tailf:cli-drop-node-name;
          tailf:cli-no-value-on-delete;
          type string {
            tailf:info
              "<conditions>;;Conditions separated by a semi-colon";
          }
        }
        leaf actions {
          tailf:cli-suppress-no;
          tailf:cli-drop-node-name;
          tailf:cli-no-value-on-delete;
          type string {
            tailf:info
              "<actions>;;Actions separated by a semi-colon";
          }
        }
        leaf application {
          tailf:cli-suppress-no;
          tailf:cli-no-value-on-delete;
          tailf:cli-no-name-on-delete;
          type string;
        }
      }
      list vlan {
        tailf:cli-diff-create-after "../vr" {
          tailf:xpath-root 3;
          tailf:cli-when-target-create;
        }
        tailf:cli-diff-delete-before "../vr" {
          tailf:xpath-root 3;
          tailf:cli-when-target-delete;
        }
        tailf:info
          "VLAN list (1-4094)";
        tailf:cli-compact-syntax;
        tailf:cli-suppress-mode;
        key "id";
        leaf id {
          type string {
            tailf:info
              "<vlan_name>;;VLAN Name";
          }
        }
        leaf vr {
          tailf:cli-no-value-on-delete;
          tailf:cli-no-name-on-delete;
          type string {
            tailf:info
              "<vr-name>;;Virtual router name";
          }
        }
      }
      list vr {
        tailf:info
          "Virtual router";
        tailf:cli-compact-syntax;
        tailf:cli-suppress-mode;
        tailf:cli-delete-when-empty;
        key "id";
        leaf id {
          type string {
            tailf:info
              "<vr-name>;;Virtual router name";
          }
        }
      }
      leaf-list qosprofile {
        tailf:cli-list-syntax;
        tailf:info
          "qosprofile";
        type string {
          tailf:info
            "<qosprofile>;;QOS profile";
        }
      }
      container log {
        tailf:info
          "Configure log service";
        leaf-list filter {
          tailf:cli-list-syntax;
          tailf:info
            "Create a filter";
          type string {
            tailf:info
              "<name>;;Name of the filter to create";
          }
        }
        container target {
          tailf:info
            "Create a target";
          leaf-list upm {
            tailf:cli-diff-delete-before "../../filter" {
              tailf:xpath-root 3;
              tailf:cli-when-target-delete;
            }
            tailf:cli-diff-modify-before "../../filter" {
              tailf:xpath-root 3;
              tailf:cli-when-target-modify;
            }
            tailf:cli-diff-delete-before "/extreme-xos:create/upm/profile" {
              tailf:xpath-root 3;
              tailf:cli-when-target-delete;
            }
            tailf:cli-diff-create-after "/extreme-xos:create/upm/profile" {
              tailf:xpath-root 3;
              tailf:cli-when-target-create;
            }
            tailf:cli-diff-delete-before "/extreme-xos:create/upm/profile/commands" {
              tailf:xpath-root 3;
              tailf:cli-when-target-delete;
            }
            tailf:cli-diff-create-after "/extreme-xos:create/upm/profile/commands" {
              tailf:xpath-root 3;
              tailf:cli-when-target-set;
            }
            tailf:cli-list-syntax;
            tailf:info
              "Type of the target is upm";
            type string {
              tailf:info
                "<upm_profile_name>;;Name of an already existing upm profile";
            }
          }
        }
      }
      container upm {
        tailf:info
          "Profile";
        list profile {
          extreme-xos:remove-before-change;
          tailf:meta-data "! meta-data :: turbo :: no-prompt-after-send";
          tailf:cli-explicit-exit;
          tailf:cli-exit-command ".";
          tailf:info
            "UPM profile";
          key "name";
          leaf name {
            type string {
              tailf:info
                "<profile-name>;;name";
            }
          }
          leaf commands {
            tailf:cli-drop-node-name;
            tailf:cli-full-command;
            tailf:cli-multi-value;
            tailf:cli-preformatted;
            extreme-xos:upm-list-out;
            type string {
              tailf:info
                "\"command1
                 command
                 command3
                 ...\" - commands quoted string, '
                 ' separated";
            }
          }
        }
      }
      list stpd {
        tailf:info
          "STP domain";
        tailf:cli-compact-syntax;
        tailf:cli-suppress-mode;
        tailf:cli-delete-when-empty;
        key "name";
        leaf name {
          type string {
            tailf:info
              "<stpd_name>;;STP domain name";
          }
        }
      }
    }
    container configure {
      tailf:ncs-device-type "cli-ned";
      tailf:display-when "not(../../ncs:module) or ../../ncs:module[ncs:name='tailf-ned-extreme-xos']";
      extreme-xos:delete-with "unconfigure";
      extreme-xos:trim-delete-if-match "unconfigure vlan \\S* tag";
      extreme-xos:trim-delete-if-match "unconfigure timezone.*";
      extreme-xos:trim-delete-if-match "unconfigure account.*";
      extreme-xos:trim-delete-if-match "unconfigure log target upm.*";
      list access-list {
        tailf:cli-diff-create-after "/extreme-xos:create/access-list" {
          tailf:xpath-root 3;
          tailf:cli-when-target-create;
        }
        tailf:cli-diff-delete-before "/extreme-xos:create/access-list" {
          tailf:xpath-root 3;
          tailf:cli-when-target-delete;
        }
        tailf:info
          "Access list";
        tailf:cli-compact-syntax;
        tailf:cli-remove-before-change;
        tailf:cli-sequence-commands {
          tailf:cli-reset-siblings;
        }
        tailf:cli-suppress-mode;
        key "aclname";
        leaf aclname {
          type string {
            tailf:info
              "<aclname>;;ACL policy file name";
          }
        }
        leaf any {
          tailf:cli-no-name-on-delete;
          tailf:cli-no-value-on-delete;
          tailf:info
            "Apply the ACL to wildcard, including all VLANs and all ports";
          type enumeration {
            enum "egress" {
              tailf:info
                "Acls applied to egress";
            }
            enum "ingress" {
              tailf:info
                "Acls applied to ingress";
            }
          }
        }
      }
      container snmp {
        tailf:info
          "Simple network Management Protocol";
        container access-profile {
          tailf:info
            "Access Profile";
          list add {
            tailf:info
              "Add";
            tailf:cli-diff-create-after "/extreme-xos:create/access-list" {
              tailf:xpath-root 3;
              tailf:cli-when-target-create;
            }
            tailf:cli-diff-delete-before "/extreme-xos:create/access-list" {
              tailf:xpath-root 3;
              tailf:cli-when-target-delete;
            }
            tailf:cli-compact-syntax;
            tailf:cli-suppress-mode;
            tailf:cli-remove-before-change;
            tailf:cli-sequence-commands;
            tailf:cli-delete-when-empty;
            key "rule";
            leaf rule {
              type string {
                tailf:info
                  "<rule>;;Access-list rule Name";
              }
            }
            leaf condition {
              tailf:cli-drop-node-name;
              tailf:cli-no-value-on-delete;
              type enumeration {
                enum "first" {
                  tailf:info
                    "Rule to be added as first rule";
                }
                enum "before" {
                  tailf:info
                    "Rule to be added before rule";
                }
                enum "after" {
                  tailf:info
                    "Rule to be added after rule";
                }
              }
            }
            leaf previous_rule {
              tailf:cli-no-value-on-delete;
              tailf:cli-drop-node-name;
              tailf:non-strict-leafref {
                path "/ncs:devices/ncs:device/ncs:config/extreme-xos:configure/snmp/access-profile/add/rule" {
                  tailf:xpath-root 3;
                }
              }
              type string {
                tailf:info
                  "<previous_rule>;;Previously added rule";
              }
            }
          }
        }
        leaf sysContact {
          extreme-xos:replace-delete-output "unconfigure snmp sysContact :: configure snmp sysContact \"support@extremenetworks.com, +1 888 257 3000\"";
          tailf:cli-no-value-on-delete;
          tailf:info
            "System Contact";
          type string {
            tailf:info
              "<sysName>;;System Contact";
          }
          default "support@extremenetworks.com, +1 888 257 3000";
        }
        leaf sysLocation {
          extreme-xos:replace-delete-output "unconfigure snmp sysLocation :: configure snmp sysLocation \"NO LOCATION PROVIDED\"";
          tailf:cli-no-value-on-delete;
          tailf:info
            "System Location";
          type string {
            tailf:info
              "<sysName>;;System Location";
          }
          default "NO LOCATION PROVIDED";
        }
        leaf sysName {
          extreme-xos:replace-delete-output "unconfigure snmp sysName :: configure snmp sysName \"EXOS-Switch\"";
          tailf:cli-no-value-on-delete;
          tailf:info
            "System Name";
          type string {
            tailf:info
              "<sysName>;;System Name";
          }
          default "EXOS-Switch";
        }
      }
      container snmpv3 {
        tailf:info
          "Configure SNMPv3";
        leaf engine-id {
          tailf:cli-no-value-on-delete;
          tailf:cli-no-name-on-delete;
          tailf:info
            "Configure SNMP engine-id";
          type yang:hex-string {
            tailf:info
              "<hex_engine_id>;;Engine-id (in hexadecimal)";
          }
        }
        container add {
          tailf:info
            "Add";
          list access {
            tailf:info
              "Access";
            tailf:cli-compact-syntax;
            tailf:cli-suppress-mode;
            key "group_name sec-model sec-level";
            leaf group_name {
              type string {
                tailf:info
                  "hex|group_name>;;Following value is to be specified in hexadecimal
                          Group name (in ASCII)";
              }
            }
            leaf sec-model {
              tailf:cli-expose-key-name;
              tailf:info
                "Security Model";
              type enumeration {
                enum "snmpv1";
                enum "snmpv2c";
                enum "usm";
              }
            }
            leaf sec-level {
              tailf:cli-expose-key-name;
              tailf:info
                "Security Level";
              type enumeration {
                enum "authnopriv";
                enum "noauth";
                enum "priv";
              }
            }
            leaf read-view {
              tailf:cli-no-value-on-delete;
              tailf:cli-no-name-on-delete;
              tailf:info
                "Read View";
              type string {
                tailf:info
                  "hex|<read_view_name>;;Following value is to be specified in hexadecimal
                       Read View Name (in ASCII)";
              }
            }
            leaf write-view {
              tailf:cli-no-value-on-delete;
              tailf:cli-no-name-on-delete;
              tailf:info
                "Write View";
              type string {
                tailf:info
                  "hex|<write-view>;;Following value is to be specified in hexadecimal
                       Write View Name (in ASCII)";
              }
            }
            leaf notify-view {
              tailf:cli-no-value-on-delete;
              tailf:cli-no-name-on-delete;
              tailf:info
                "Notify View";
              type string {
                tailf:info
                  "hex|<notify-view>;;Following value is to be specified in hexadecimal
                       Notify View Name (in ASCII)";
              }
            }
          }
          list community {
            tailf:info
              "Community";
            tailf:cli-compact-syntax;
            tailf:cli-suppress-mode;
            key "community_index";
            leaf community_index {
              type string {
                tailf:info
                  "hex|<community_index>;;Following value is to be specified in hexadecimal
                          Community Index (in ASCII)";
              }
            }
            leaf name {
              tailf:cli-suppress-no;
              tailf:cli-no-value-on-delete;
              tailf:cli-no-name-on-delete;
              tailf:info
                "Community name";
              type string {
                tailf:info
                  "<community_name>;;Community name (in ASCII)";
              }
            }
            uses user-grouping;
          }
          list group {
            tailf:info
              "Group";
            tailf:cli-compact-syntax;
            tailf:cli-suppress-mode;
            key "group_name user sec-model";
            leaf group_name {
              type string {
                tailf:info
                  "hex|<<group_name>>;;Following value is to be specified in hexadecimal
                          Group Name (in ASCII)";
              }
            }
            leaf user {
              tailf:cli-expose-key-name;
              tailf:info
                "User";
              type string {
                tailf:info
                  "hex|<user_name>;;Following value is to be specified in hexadecimal
                          User Name (in ASCII)";
              }
            }
            leaf sec-model {
              tailf:cli-expose-key-name;
              tailf:info
                "Security Model";
              type enumeration {
                enum "snmpv1";
                enum "snmpv2c";
                enum "usm";
              }
            }
          }
          list target-addr {
            tailf:info
              "Target Address";
            tailf:cli-compact-syntax;
            tailf:cli-suppress-mode;
            key "addr_name";
            leaf addr_name {
              type string {
                tailf:info
                  "<addr_name>;;Address Name (in ASCII)";
              }
            }
            leaf param {
              tailf:cli-suppress-no;
              tailf:cli-no-value-on-delete;
              tailf:cli-no-name-on-delete;
              tailf:info
                "Param";
              type string {
                tailf:info
                  "<param_name>;;Param name (in ASCII)";
              }
            }
            leaf ipaddress {
              tailf:cli-suppress-no;
              tailf:cli-no-value-on-delete;
              tailf:cli-no-name-on-delete;
              tailf:info
                "IP address (IPv4 or IPv6 Address)";
              type inet:ip-address;
            }
            leaf transport-port {
              tailf:cli-suppress-no;
              tailf:cli-no-value-on-delete;
              tailf:cli-no-name-on-delete;
              tailf:info
                "Transport port";
              type uint32 {
                tailf:info
                  "<port_number>;;Port number";
              }
            }
            leaf from {
              tailf:cli-diff-set-after "/extreme-xos:configure/vlan/ipaddress/ipaddress" {
                tailf:xpath-root 3;
                tailf:cli-when-target-create;
              }
              tailf:cli-diff-delete-before "/extreme-xos:configure/vlan/ipaddress/ipaddress" {
                tailf:xpath-root 3;
                tailf:cli-when-target-delete;
              }
              tailf:cli-suppress-no;
              tailf:cli-no-value-on-delete;
              tailf:cli-no-name-on-delete;
              tailf:info
                "Src IP address (IPv4 or IPv6 Address)";
              type inet:ip-address {
                tailf:info
                  "<src_ip_address>;;Src IPv4 address";
              }
            }
            leaf-list tag-list {
              tailf:cli-suppress-no;
              tailf:cli-no-value-on-delete;
              tailf:cli-no-name-on-delete;
              tailf:info
                "Tag list";
              tailf:cli-range-list-syntax;
              tailf:cli-flat-list-syntax;
              type string {
                tailf:info
                  "<tag_list>;;List of tags separated by commas";
              }
            }
          }
          list target-params {
            tailf:info
              "Target Params";
            tailf:cli-compact-syntax;
            tailf:cli-suppress-mode;
            key "group_name";
            leaf group_name {
              type string {
                tailf:info
                  "<param_name>;;Param Name (in ASCII)";
              }
            }
            uses user-grouping;
            leaf mp-model {
              tailf:cli-suppress-no;
              tailf:cli-no-value-on-delete;
              tailf:cli-no-name-on-delete;
              tailf:info
                "Message Processing Model";
              type enumeration {
                enum "snmpv1";
                enum "snmpv2c";
                enum "snmpv3";
              }
            }
            leaf sec-model {
              tailf:cli-suppress-no;
              tailf:cli-no-value-on-delete;
              tailf:cli-no-name-on-delete;
              tailf:info
                "Security Model";
              type enumeration {
                enum "snmpv1";
                enum "snmpv2c";
                enum "usm";
              }
            }
            leaf sec-level {
              tailf:cli-suppress-no;
              tailf:cli-no-value-on-delete;
              tailf:cli-no-name-on-delete;
              tailf:info
                "Security Level";
              type enumeration {
                enum "authnopriv";
                enum "noauth";
                enum "priv";
              }
            }
          }
          list user {
            extreme-xos:replace-input "(\\s+engine-id [0-9a-f:]+) :: ";
            tailf:info
              "User";
            tailf:cli-compact-syntax;
            tailf:cli-suppress-mode;
            key "user_name";
            leaf user_name {
              type string {
                tailf:info
                  "hex|<user_name>;;Following value is to be specified in hexadecimal
                          User Name (in ASCII)";
              }
            }
            leaf authentication {
              tailf:cli-suppress-no;
              tailf:cli-no-value-on-delete;
              tailf:cli-no-name-on-delete;
              tailf:info
                "Authentication scheme";
              type enumeration {
                enum "md5" {
                  tailf:info
                    "MD5";
                }
                enum "sha" {
                  tailf:info
                    "SHA";
                }
              }
            }
            container auth-encrypted {
              tailf:cli-suppress-no;
              tailf:cli-no-name-on-delete;
              tailf:info
                "Authentication secret is to be entered in encrypted form";
              tailf:cli-flatten-container;
              leaf localized-key {
                tailf:cli-suppress-no;
                tailf:cli-no-value-on-delete;
                tailf:cli-no-name-on-delete;
                tailf:info
                  "Following value is a MD5 or SHA hash of the engine-id and user's password";
                cli:secret " auth-encrypted localized-key (\\S+)" {
                  cli:arguments "always-encrypted";
                }
                extreme-xos:send-secret;
                tailf:cli-disallow-value "privacy";
                type string {
                  tailf:info
                    "<auth_localized_key>|<auth_password>;;Authentication localized key (in hexadecimal)| Authentication Password (in ASCII)";
                }
              }
            }
            leaf privacy {
              tailf:cli-suppress-no;
              tailf:cli-no-value-on-delete;
              tailf:cli-no-name-on-delete;
              tailf:info
                "Privacy";
              type enumeration {
                enum "3des" {
                  tailf:info
                    "Specifies the use of the 168-bit 3DES algorithm for encryption";
                }
                enum "aes" {
                  tailf:info
                    "Specifies the use of the AES algorithm for encryption";
                }
                enum "des" {
                  tailf:info
                    "Specifies the use of the 56-bit DES algorithm for encryption(default)";
                }
              }
            }
            leaf aes-bits {
              tailf:cli-suppress-no;
              tailf:cli-no-value-on-delete;
              tailf:cli-no-name-on-delete;
              tailf:cli-drop-node-name;
              when "../privacy = 'aes'" {
                tailf:xpath-root 3;
              }
              type enumeration {
                enum "128" {
                  tailf:info
                    "Specifies the use of the 128-bit AES algorithm for encryption";
                }
                enum "192" {
                  tailf:info
                    "Specifies the use of the 192-bit AES algorithm for encryption";
                }
                enum "256" {
                  tailf:info
                    "Specifies the use of the 256-bit AES algorithm for encryption";
                }
              }
            }
            leaf privacy-encrypted {
              tailf:cli-suppress-no;
              tailf:cli-no-name-on-delete;
              tailf:info
                "Privacy Password is to be entered in encrypted form";
              type empty;
            }
            leaf localized-key {
              tailf:cli-suppress-no;
              tailf:cli-no-value-on-delete;
              tailf:cli-no-name-on-delete;
              tailf:info
                "Following value is a MD5 or SHA hash of the engine-id and user's password";
              cli:secret " privacy-encrypted localized-key (\\S+)" {
                cli:arguments "always-encrypted";
              }
              extreme-xos:send-secret;
              type string {
                tailf:info
                  "<auth_localized_key>|<auth_password>;;Authentication localized key (in hexadecimal)| Authentication Password (in ASCII)";
              }
            }
          }
        }
      }
      list vlan {
        tailf:info
          "VLAN list (1-4094)";
        tailf:cli-suppress-mode;
        tailf:cli-delete-when-empty;
        key "id";
        leaf id {
          type string {
            tailf:info
              "<vlan_name>;;VLAN Name";
          }
        }
        container delete {
          when "../id = 'default'" {
            tailf:xpath-root 3;
          }
          tailf:info
            "Delete entities from VLAN";
          list ports {
            tailf:cli-diff-set-after "/extreme-xos:create/vlan" {
              tailf:xpath-root 3;
              tailf:cli-when-target-create;
            }
            tailf:cli-diff-delete-before "/extreme-xos:create/vlan" {
              tailf:xpath-root 3;
              tailf:cli-when-target-delete;
            }
            tailf:info
              "port list";
            tailf:cli-suppress-mode;
            tailf:cli-compact-syntax;
            tailf:cli-range-list-syntax;
            key "id";
            leaf id {
              type union {
                type uint32 {
                  tailf:info
                    "<port_list>;;Port list";
                }
                type enumeration {
                  enum "all" {
                    tailf:info
                      "all";
                  }
                }
              }
            }
          }
        }
        container add {
          tailf:info
            "Add entities to VLAN";
          list ports {
            tailf:cli-diff-set-after "/extreme-xos:create/vlan" {
              tailf:xpath-root 3;
              tailf:cli-when-target-create;
            }
            tailf:cli-diff-delete-before "/extreme-xos:create/vlan" {
              tailf:xpath-root 3;
              tailf:cli-when-target-delete;
            }
            tailf:cli-diff-create-before "../../tag" {
              tailf:xpath-root 3;
              tailf:cli-when-target-delete;
            }
            tailf:cli-diff-create-after "../../tag" {
              tailf:xpath-root 3;
              tailf:cli-when-target-set;
            }
            tailf:cli-diff-create-after "/extreme-xos:configure/vr/add/ports" {
              tailf:xpath-root 3;
              tailf:cli-when-target-delete;
            }
            tailf:info
              "Ports in this VLAN to add";
            tailf:cli-suppress-mode;
            tailf:cli-compact-syntax;
            tailf:cli-range-list-syntax;
            key "id";
            leaf id {
              type union {
                type uint32 {
                  tailf:info
                    "<port_list>;;Port list";
                }
                type enumeration {
                  enum "all" {
                    tailf:info
                      "all";
                  }
                }
              }
            }
            choice tag {
              leaf untagged {
                tailf:cli-no-name-on-delete;
                tailf:info
                  "untagged";
                type empty;
              }
              leaf tagged {
                tailf:cli-no-name-on-delete;
                tailf:info
                  "untagged";
                type empty;
              }
            }
          }
        }
        container ipaddress {
          tailf:info
            "IP address";
          tailf:cli-compact-syntax;
          tailf:cli-sequence-commands {
            tailf:cli-reset-siblings;
          }
          leaf ipaddress {
            tailf:cli-diff-set-after "/extreme-xos:create/vlan" {
              tailf:xpath-root 3;
              tailf:cli-when-target-create;
            }
            tailf:cli-diff-delete-before "/extreme-xos:create/vlan" {
              tailf:xpath-root 3;
              tailf:cli-when-target-delete;
            }
            tailf:cli-diff-set-before "../../tag" {
              tailf:xpath-root 3;
              tailf:cli-when-target-delete;
            }
            tailf:cli-remove-before-change;
            tailf:cli-suppress-no;
            tailf:cli-no-value-on-delete;
            tailf:cli-drop-node-name;
            type inet:ip-address {
              tailf:info
                "<ipaddress>;;IP address";
            }
          }
          leaf netmask {
            tailf:cli-suppress-no;
            tailf:cli-no-value-on-delete;
            tailf:cli-drop-node-name;
            type inet:ip-address {
              tailf:info
                "<netmask>;;IP netmask";
            }
          }
        }
        leaf tag {
          tailf:cli-diff-set-after "/extreme-xos:create/vlan" {
            tailf:xpath-root 3;
            tailf:cli-when-target-create;
          }
          tailf:cli-diff-delete-before "/extreme-xos:create/vlan" {
            tailf:xpath-root 3;
            tailf:cli-when-target-delete;
          }
          tailf:cli-full-command;
          tailf:cli-no-value-on-delete;
          tailf:info
            "VLAN tag";
          type uint16 {
            tailf:info
              "<tag>;;VLAN tag ID between 1 and 4094";
          }
        }
        leaf description {
          tailf:cli-diff-set-after "/extreme-xos:create/vlan" {
            tailf:xpath-root 3;
            tailf:cli-when-target-create;
          }
          tailf:cli-diff-delete-before "/extreme-xos:create/vlan" {
            tailf:xpath-root 3;
            tailf:cli-when-target-delete;
          }
          tailf:cli-no-value-on-delete;
          tailf:cli-full-command;
          tailf:info
            "Description string up to 64 characters";
          type string {
            tailf:info
              "<vlan-desc>;;Description string in quotes up to 64 characters";
          }
          default "none";
        }
      }
      list vr {
        tailf:info
          "Virtual router";
        tailf:cli-compact-syntax;
        tailf:cli-suppress-mode;
        tailf:cli-delete-when-empty;
        key "id";
        leaf id {
          type string {
            tailf:info
              "<vr-name>;;Virtual router name";
          }
        }
        container delete {
          when "../id = 'VR-Default'" {
            tailf:xpath-root 3;
          }
          tailf:info
            "Delete configuration";
          uses portList-grouping;
        }
        container add {
          tailf:info
            "Add configuration";
          leaf-list ports {
            tailf:cli-diff-create-after "/extreme-xos:create/vr" {
              tailf:xpath-root 3;
              tailf:cli-when-target-create;
            }
            tailf:cli-diff-delete-before "/extreme-xos:create/vr" {
              tailf:xpath-root 3;
              tailf:cli-when-target-delete;
            }
            tailf:info
              "Physical ports";
            tailf:cli-range-list-syntax;
            type uint32 {
              tailf:info
                "<portlist>;;List of ports separated by comma";
            }
          }
        }
      }
      container iproute {
        tailf:info
          "IP routing module";
        container add {
          tailf:info
            "Add route";
          container default {
            tailf:info
              "default route";
            leaf gateway {
              tailf:cli-drop-node-name;
              type inet:ip-address {
                tailf:info
                  "<gateway>;;gateway address";
              }
            }
          }
          list route {
            tailf:cli-drop-node-name;
            tailf:cli-suppress-mode;
            key "address netmask gateway";
            leaf address {
              type inet:ip-address {
                tailf:info
                  "<ipaddress>;;Destination address";
              }
            }
            leaf netmask {
              type inet:ip-address {
                tailf:info
                  "<netmask>;;IP address netmask";
              }
            }
            leaf gateway {
              type inet:ip-address {
                tailf:info
                  "<gateway>;;gateway address";
              }
            }
          }
        }
      }
      container tacacs {
        extreme-xos:replace-delete-output "unconfigure tacacs (\\w+) server :: unconfigure tacacs server $1";
        extreme-xos:trim-delete-if-match "unconfigure.*shared-secret";
        tailf:info
          "Configure TACACS+ Server";
        uses tacacs-grouping;
        leaf priv-lvl {
          extreme-xos:replace-delete-output "unconfigure tacacs priv-lvl :: configure tacacs priv-lvl optional";
          tailf:ned-default-handling trim;
          tailf:info
            "Privilege level attribute of authorization request.";
          tailf:cli-no-value-on-delete;
          type enumeration {
            enum "optional" {
              tailf:info
                "Allow login with read-only privilege if priv-lvl is not provided. (Default)";
            }
            enum "required" {
              tailf:info
                "Fail login attempt if priv-lvl attribute is not provided";
            }
          }
          default "optional";
        }
      }
      container tacacs-accounting {
        extreme-xos:replace-delete-output "unconfigure tacacs-accounting (\\w+) server :: unconfigure tacacs-accounting server $1";
        extreme-xos:trim-delete-if-match "unconfigure.*shared-secret";
        tailf:info
          "Configure TACACS+ Accounting Server";
        uses tacacs-grouping;
      }
      container banner {
        tailf:info
          "System login banner";
        container before-login {
          tailf:info
            "Banner to be displayed before login (default)";
          leaf save-to-configuration {
            tailf:cli-no-value-on-delete;
            extreme-xos:replace-delete-output "unconfigure banner before-login save-to-configuration :: configure banner before-login save-to-configuration  ";
            extreme-xos:multi-line-banner;
            tailf:info
              "Save the before login banner to the configuration file as well as non-volatile memory";
            type string;
          }
        }
        leaf after-login {
          tailf:info
            "Banner to be displayed after login";
          tailf:cli-no-value-on-delete;
          extreme-xos:replace-delete-output "unconfigure banner after-login :: configure banner after-login  ";
          extreme-xos:multi-line-banner;
          type string;
        }
      }
      container syslog {
        tailf:info
          "Remote syslog target";
        list add {
          tailf:cli-diff-create-after "/extreme-xos:create/vr" {
            tailf:xpath-root 3;
            tailf:cli-when-target-create;
          }
          tailf:cli-diff-delete-before "/extreme-xos:create/vr" {
            tailf:xpath-root 3;
            tailf:cli-when-target-delete;
          }
          tailf:info
            "Add a syslog target";
          tailf:cli-compact-syntax;
          tailf:cli-suppress-mode;
          key "ipPort vr local";
          leaf ipPort {
            type string {
              tailf:info
                "<ipPort>;;Remote syslog server IPv4 address : UDP Port";
            }
          }
          leaf vr {
            tailf:cli-expose-key-name;
            tailf:info
              "Virtual router ID";
            type string {
              tailf:info
                "<vr_name>;;Virtual router ID";
            }
          }
          leaf local {
            tailf:cli-drop-node-name;
            type string {
              tailf:info
                "<local>;;Remote syslog server facility";
            }
          }
        }
      }
      container log {
        tailf:info
          "Configure log service";
        container target {
          tailf:info
            "Configure target";
          list syslog {
            extreme-xos:replace-delete-output "unconfigure log target syslog :: configure syslog delete :: format,filter,match,from";
            extreme-xos:trim-delete-if-match "unconfigure log target syslog.*filter.*";
            extreme-xos:trim-delete-if-match "unconfigure log target syslog.*match.*";
            extreme-xos:trim-delete-if-match "unconfigure log target syslog.*from.*";
            tailf:cli-diff-create-after "/extreme-xos:create/vr" {
              tailf:xpath-root 3;
              tailf:cli-when-target-create;
            }
            tailf:cli-diff-delete-before "/extreme-xos:create/vr" {
              tailf:xpath-root 3;
              tailf:cli-when-target-delete;
            }
            tailf:cli-diff-create-after "/extreme-xos:configure/syslog/add" {
              tailf:xpath-root 3;
              tailf:cli-when-target-create;
            }
            tailf:cli-diff-delete-before "/extreme-xos:configure/syslog/add" {
              tailf:xpath-root 3;
              tailf:cli-when-target-delete;
            }
            tailf:info
              "Remote syslog target";
            tailf:cli-compact-syntax;
            tailf:cli-suppress-mode;
            tailf:cli-delete-when-empty;
            key "ipPort vr local";
            leaf ipPort {
              type string {
                tailf:info
                  "<ipPort>;;Remote syslog server IPv4 address : UDP Port";
              }
            }
            leaf vr {
              tailf:cli-expose-key-name;
              tailf:info
                "Virtual router ID";
              type string {
                tailf:info
                  "<vr_name>;;Virtual router ID";
              }
            }
            leaf local {
              type string {
                tailf:info
                  "<local>;;Remote syslog server facility";
              }
            }
            leaf from {
              tailf:cli-diff-set-after "/extreme-xos:configure/vlan/ipaddress/ipaddress" {
                tailf:xpath-root 3;
                tailf:cli-when-target-create;
              }
              tailf:cli-diff-delete-before "/extreme-xos:configure/vlan/ipaddress/ipaddress" {
                tailf:xpath-root 3;
                tailf:cli-when-target-delete;
              }
              tailf:info
                "Configure specific local source IP address";
              tailf:cli-full-command;
              type inet:ip-address {
                tailf:info
                  "<source-ip-address>;;Local source address to use";
              }
            }
            container filter {
              tailf:cli-compact-syntax;
              tailf:cli-sequence-commands {
                tailf:cli-reset-siblings;
              }
              tailf:info
                "Filter";
              leaf filter {
                tailf:cli-diff-set-after "/extreme-xos:configure/syslog/add" {
                  tailf:xpath-root 3;
                  tailf:cli-when-target-create;
                }
                tailf:cli-diff-delete-before "/extreme-xos:configure/syslog/add" {
                  tailf:xpath-root 3;
                  tailf:cli-when-target-delete;
                }
                tailf:cli-drop-node-name;
                type string {
                  tailf:info
                    "<filter-name>;filter name";
                }
              }
              leaf severity {
                tailf:cli-no-name-on-delete;
                tailf:cli-no-value-on-delete;
                tailf:info
                  "Configure a severity threshold for this target";
                type string {
                  tailf:info
                    "<severity>;;Severity value to use";
                }
              }
            }
            container format {
              tailf:info
                "Display format";
              tailf:cli-compact-syntax;
              tailf:cli-sequence-commands {
                tailf:cli-reset-siblings;
              }
              leaf timestamp {
                tailf:cli-diff-set-after "/extreme-xos:configure/syslog/add" {
                  tailf:xpath-root 3;
                  tailf:cli-when-target-create;
                }
                tailf:cli-diff-delete-before "/extreme-xos:configure/syslog/add" {
                  tailf:xpath-root 3;
                  tailf:cli-when-target-delete;
                }
                tailf:cli-no-name-on-delete;
                tailf:cli-no-value-on-delete;
                tailf:info
                  "Configure timestamp format";
                type enumeration {
                  enum "hundredths" {
                    tailf:info
                      "Time format as hh:mm:ss.HH (e.g. 12:00:23.96)";
                  }
                  enum "none" {
                    tailf:info
                      "Do not display anything";
                  }
                  enum "seconds" {
                    tailf:info
                      "Time format as hh:mm:ss (e.g. 12:00:23)";
                  }
                }
              }
              leaf date {
                tailf:cli-no-name-on-delete;
                tailf:cli-no-value-on-delete;
                tailf:info
                  "Configure date format";
                type enumeration {
                  enum "Mmm-dd" {
                    tailf:info
                      "Date format as specified in RFC 3164 (e.g. Jan 14)";
                  }
                  enum "dd-Mmm-yyyy" {
                    tailf:info
                      "Date format as 14-Jan-2003";
                  }
                  enum "dd-mm-yyyy" {
                    tailf:info
                      "Date format as 14-01-2003";
                  }
                  enum "mm/dd/yyyy" {
                    tailf:info
                      "Date format as 01/14/2003";
                  }
                  enum "none" {
                    tailf:info
                      "Do not display anything";
                  }
                }
              }
              leaf event-name {
                tailf:cli-no-name-on-delete;
                tailf:cli-no-value-on-delete;
                tailf:info
                  "Configure event name format ";
                tailf:cli-optional-in-sequence;
                tailf:cli-break-sequence-commands;
                type enumeration {
                  enum "component" {
                    tailf:info
                      "Display component name";
                  }
                  enum "condition" {
                    tailf:info
                      "Display component and condition name";
                  }
                  enum "none" {
                    tailf:info
                      "Do not display anything";
                  }
                }
              }
              leaf priority {
                tailf:cli-no-name-on-delete;
                tailf:info
                  "Enable or disable the display of the priority";
                type empty;
              }
              leaf host-name {
                tailf:cli-no-name-on-delete;
                tailf:info
                  "Enable or disable the display of the host name";
                type empty;
              }
              leaf severity {
                tailf:cli-no-name-on-delete;
                tailf:info
                  "Enable or disable the display of the severity";
                type empty;
              }
              leaf tag-name {
                tailf:cli-no-name-on-delete;
                tailf:info
                  "Enable or disable the display of the tag name";
                type empty;
              }
            }
            container match {
              tailf:info
                "Configure regular expression";
              choice regex-choice {
                leaf any {
                  tailf:cli-diff-set-after "/extreme-xos:configure/syslog/add" {
                    tailf:xpath-root 3;
                    tailf:cli-when-target-create;
                  }
                  tailf:cli-diff-delete-before "/extreme-xos:configure/syslog/add" {
                    tailf:xpath-root 3;
                    tailf:cli-when-target-delete;
                  }
                  tailf:info
                    "Do not match any regular expression";
                  type empty;
                }
                leaf regex {
                  tailf:cli-diff-set-after "/extreme-xos:configure/syslog/add" {
                    tailf:xpath-root 3;
                    tailf:cli-when-target-create;
                  }
                  tailf:cli-diff-delete-before "/extreme-xos:configure/syslog/add" {
                    tailf:xpath-root 3;
                    tailf:cli-when-target-delete;
                  }
                  tailf:cli-drop-node-name;
                  tailf:cli-disallow-value "any";
                  type string {
                    tailf:info
                      "<regex>;;Regular expression to match";
                  }
                }
              }
            }
          }
          list upm {
            tailf:cli-diff-delete-before "/extreme-xos:create/upm/profile" {
              tailf:xpath-root 3;
              tailf:cli-when-target-delete;
            }
            tailf:cli-diff-create-after "/extreme-xos:create/upm/profile" {
              tailf:xpath-root 3;
              tailf:cli-when-target-create;
            }
            tailf:cli-diff-delete-before "/extreme-xos:create/log/target/upm" {
              tailf:xpath-root 3;
              tailf:cli-when-target-delete;
            }
            tailf:cli-diff-create-after "/extreme-xos:create/log/target/upm" {
              tailf:xpath-root 3;
              tailf:cli-when-target-create;
            }
            tailf:cli-diff-delete-before "/extreme-xos:create/log/filter" {
              tailf:xpath-root 3;
              tailf:cli-when-target-delete;
            }
            tailf:cli-diff-delete-before "/extreme-xos:create/log/filter" {
              tailf:xpath-root 3;
              tailf:cli-when-target-modify;
            }
            tailf:info
              "Sending messages to UPM as events";
            tailf:cli-compact-syntax;
            tailf:cli-suppress-mode;
            tailf:cli-delete-when-empty;
            key "name";
            leaf name {
              tailf:non-strict-leafref {
                path "/ncs:devices/ncs:device/ncs:config/extreme-xos:create/log/target/upm" {
                  tailf:xpath-root 3;
                }
              }
              type string {
                tailf:info
                  "<upm_profile_name>;;UPM Profile Name";
              }
            }
            leaf filter {
              tailf:info
                "Filter";
              tailf:cli-diff-delete-before "/extreme-xos:create/log/filter" {
                tailf:xpath-root 3;
                tailf:cli-when-target-delete;
              }
              tailf:non-strict-leafref {
                path "/ncs:devices/ncs:device/ncs:config/extreme-xos:create/log/filter" {
                  tailf:xpath-root 3;
                }
              }
              type string {
                tailf:info
                  "<name>;;Name of the filter to configure";
              }
            }
            leaf severity {
              tailf:cli-case-insensitive;
              tailf:info
                "Configure a severity threshold for this target";
              type enumeration {
                enum "critical";
                enum "debug-data";
                enum "debug-summary";
                enum "debug-verbose";
                enum "error";
                enum "info";
                enum "notice";
                enum "warning";
              }
            }
          }
        }
        list filter {
          tailf:cli-diff-delete-before "/extreme-xos:create/log/filter" {
            tailf:xpath-root 3;
            tailf:cli-when-target-delete;
          }
          tailf:info
            "Configure filter";
          tailf:cli-compact-syntax;
          tailf:cli-suppress-mode;
          tailf:cli-delete-when-empty;
          key "name";
          leaf name {
            tailf:non-strict-leafref {
              path "/ncs:devices/ncs:device/ncs:config/extreme-xos:create/log/filter" {
                tailf:xpath-root 3;
              }
            }
            type string {
              tailf:info
                "<name>;;Name of the filter to configure";
            }
          }
          container add {
            tailf:info
              "Add event to filter";
            leaf-list events {
              extreme-xos:replace-delete-output "un(.*) add (.*) :: $1 delete $2";
              tailf:info
                "Events to add";
              tailf:cli-list-syntax;
              type string {
                tailf:info
                  "<event-component>;;Component to add or delete";
              }
            }
          }
        }
      }
      container ports {
        tailf:info
          "Ports";
        list port_list {
          tailf:cli-drop-node-name;
          tailf:cli-suppress-mode;
          tailf:cli-compact-syntax;
          tailf:cli-delete-when-empty;
          key "port";
          leaf port {
            type uint32 {
              tailf:info
                "<port_list>;;Port list";
            }
          }
          container debounce {
            tailf:cli-no-name-on-delete;
            tailf:info
              "Configure debounce time for the amount of time specified in milliseconds.";
            leaf time {
              tailf:cli-no-name-on-delete;
              tailf:cli-no-value-on-delete;
              tailf:info
                "Configure amount of time to delay link down detection.";
              type uint32 {
                tailf:info
                  "<milliseconds>;;Time in milliseconds. Range is 0 (no debouncing) to 5000.";
              }
              default "0";
            }
          }
          leaf description-string {
            tailf:cli-no-value-on-delete;
            tailf:info
              "Description string associated with the port (255 Chars limit)";
            type string {
              tailf:info
                "<string>;;Character string up to 255 characters";
            }
          }
          container rate-limit {
            tailf:info
              "Rate limiting";
            container flood {
              tailf:info
                "Flood rate limiting";
              leaf broadcast {
                extreme-xos:replace-delete-output "unconfigure (.*broadcast) \\d+ :: configure $1 no-limit";
                tailf:info
                  "Broadcast traffic";
                type union {
                  type enumeration {
                    enum "no-limit" {
                      tailf:info
                        "Unlimited rate";
                    }
                  }
                  type uint32 {
                    tailf:info
                      "<pps>;;Packets per second allowed (0-262144)";
                  }
                }
                default "no-limit";
              }
            }
          }
        }
      }
      container dns-client {
        tailf:info
          "DNS Client";
        container add {
          tailf:info
            "Add";
          list name-server {
            ordered-by user;
            tailf:cli-show-long-obu-diffs;
            tailf:cli-diff-create-after "/extreme-xos:create/vr" {
              tailf:xpath-root 3;
              tailf:cli-when-target-create;
            }
            tailf:cli-diff-delete-before "/extreme-xos:create/vr" {
              tailf:xpath-root 3;
              tailf:cli-when-target-delete;
            }
            tailf:info
              "DNS server";
            tailf:cli-suppress-mode;
            tailf:cli-compact-syntax;
            key "ip_address vr";
            leaf ip_address {
              type inet:ip-address {
                tailf:info
                  "<ip_address>;;ip address of DNS server";
              }
            }
            leaf vr {
              tailf:cli-expose-key-name;
              type string {
                tailf:info
                  "<vr_name>;;Virtual router ID";
              }
            }
          }
          list domain-suffix {
            ordered-by user;
            tailf:cli-show-long-obu-diffs;
            tailf:info
              "domain suffix";
            tailf:cli-suppress-mode;
            tailf:cli-compact-syntax;
            key "domain_name";
            leaf domain_name {
              type string {
                tailf:info
                  "<domain_name>;;Domain Name";
              }
            }
          }
        }
      }
      container sntp-client {
        tailf:info
          "Configure SNTP Client";
        container primary {
          tailf:cli-compact-syntax;
          tailf:cli-sequence-commands;
          tailf:info
            "primary server";
          uses sntpc-grouping;
        }
        container secondary {
          tailf:cli-compact-syntax;
          tailf:cli-sequence-commands;
          tailf:info
            "secondary server";
          uses sntpc-grouping;
        }
      }
      container cli {
        extreme-xos:replace-delete-output "unconfigure cli max-sessions.* :: configure cli max-sessions 8";
        tailf:info
          "Command Line Interface settings";
        leaf max-sessions {
          tailf:info
            "Maximum number of simultaneous CLI sessions";
          type uint8 {
            tailf:info
              "<num-of-sessions>;;New maximum value, range is 1 to 16";
          }
          tailf:ned-default-handling trim;
          default "8";
        }
      }
      container timezone {
        tailf:info
          "Time zone";
        tailf:cli-compact-syntax;
        tailf:cli-sequence-commands;
        leaf name {
          tailf:cli-no-value-on-delete;
          tailf:cli-no-name-on-delete;
          tailf:cli-optional-in-sequence;
          tailf:info
            "name";
          type string {
            tailf:info
              "<tz_name>;;Timezone Name";
          }
        }
        leaf gmt_offset {
          tailf:cli-no-value-on-delete;
          tailf:cli-drop-node-name;
          type uint32 {
            tailf:info
              "<GMT_offset>;;GMT Offset in minutes";
          }
        }
        leaf autodst {
          tailf:cli-no-value-on-delete;
          tailf:cli-drop-node-name;
          type enumeration {
            enum "autodst" {
              tailf:info
                "Auto Daylight Saving time";
            }
            enum "noautodst" {
              tailf:info
                "No Daylight Saving time";
            }
          }
          default "autodst";
        }
      }
      container radius {
        tailf:info
          "Configure RADIUS Server";
        list server {
          extreme-xos:replace-delete-output "(unconfigure radius) (\\d+) :: $1 server $2";
          tailf:cli-compact-syntax;
          tailf:cli-sequence-commands;
          tailf:cli-suppress-mode;
          tailf:cli-drop-node-name;
          key "index";
          leaf index {
            type uint16 {
              tailf:info
                "<index>;;RADIUS server index";
            }
          }
          // NCS expand uses statement
          container shared-secret {
            tailf:info
              "shared secret";
            tailf:cli-flatten-container;
            leaf encrypted {
              cli:secret "encrypted <SECRET>" {
                cli:arguments "always-encrypted";
              }
              extreme-xos:send-secret;
              extreme-xos:quoted-string;
              tailf:info
                "Password is Encrypted";
              type string {
                tailf:info
                  "<encrypted_secret>;;encrypted secret string";
              }
              tailf:cli-no-value-on-delete;
              tailf:cli-no-name-on-delete;
            }
            tailf:cli-no-name-on-delete;
          }
        }
        container netlogin {
          tailf:info
            "RADIUS authentication for netlogin access";
          list server {
            extreme-xos:replace-delete-output "(unconfigure radius) netlogin (\\d+) :: $1 server $2";
            tailf:cli-drop-node-name;
            tailf:cli-compact-syntax;
            tailf:cli-sequence-commands;
            tailf:cli-suppress-mode;
            key "index";
            leaf index {
              type uint16 {
                tailf:info
                  "<index>;;RADIUS server index";
              }
            }
            leaf server {
              tailf:cli-no-value-on-delete;
              tailf:cli-no-name-on-delete;
              tailf:info
                "RADIUS server";
              type inet:ip-address {
                tailf:info
                  "<host_ipaddr>;;server ip or ipv6 address";
              }
            }
            leaf udp-port {
              tailf:cli-no-value-on-delete;
              tailf:cli-drop-node-name;
              type uint16 {
                tailf:info
                  "<udp_port>;;server UDP port. Range is 1 to 65535. Default: Auth - 1812, Acct - 1813";
              }
            }
            leaf client-ip {
              tailf:cli-no-value-on-delete;
              tailf:cli-no-name-on-delete;
              tailf:info
                "client ip";
              type inet:ip-address {
                tailf:info
                  "<client_ipaddr>;;client ip or ipv6 address";
              }
            }
            // NCS expand uses statement
            leaf vr {
              tailf:cli-diff-create-after "/extreme-xos:create/vr" {
                tailf:xpath-root 3;
                tailf:cli-when-target-create;
              }
              tailf:cli-diff-delete-before "/extreme-xos:create/vr" {
                tailf:xpath-root 3;
                tailf:cli-when-target-delete;
              }
              tailf:info
                "Virtual router ID";
              type string {
                tailf:info
                  "<vr_name>;;Virtual router ID";
              }
              tailf:cli-no-value-on-delete;
              tailf:cli-no-name-on-delete;
            }
          }
          uses radius-timeout-grouping;
        }
        list dynamic-authorization {
          extreme-xos:replace-delete-output "(unconfigure.*) (\\d+) :: $1 server $2";
          tailf:info
            "Configure RADIUS Dynamic Authorization Server";
          tailf:cli-compact-syntax;
          tailf:cli-suppress-mode;
          key "index";
          leaf index {
            type uint16 {
              tailf:info
                "<index>;;RADIUS server index";
            }
          }
          container server {
            tailf:cli-compact-syntax;
            tailf:cli-sequence-commands;
            tailf:cli-no-name-on-delete;
            tailf:info
              "RADIUS server";
            leaf host {
              tailf:cli-drop-node-name;
              tailf:cli-no-value-on-delete;
              type inet:ip-address {
                tailf:info
                  "<host_ipaddr>;;server ip or ipv6 address";
              }
            }
            leaf client-ip {
              tailf:cli-no-value-on-delete;
              tailf:cli-no-name-on-delete;
              tailf:info
                "client ip";
              type inet:ip-address {
                tailf:info
                  "<client_ipaddr>;;client ip or ipv6 address";
              }
            }
            // NCS expand uses statement
            leaf vr {
              tailf:cli-diff-create-after "/extreme-xos:create/vr" {
                tailf:xpath-root 3;
                tailf:cli-when-target-create;
              }
              tailf:cli-diff-delete-before "/extreme-xos:create/vr" {
                tailf:xpath-root 3;
                tailf:cli-when-target-delete;
              }
              tailf:info
                "Virtual router ID";
              type string {
                tailf:info
                  "<vr_name>;;Virtual router ID";
              }
              tailf:cli-no-value-on-delete;
              tailf:cli-no-name-on-delete;
            }
            // NCS expand uses statement
            container shared-secret {
              tailf:info
                "shared secret";
              tailf:cli-flatten-container;
              leaf encrypted {
                cli:secret "encrypted <SECRET>" {
                  cli:arguments "always-encrypted";
                }
                extreme-xos:send-secret;
                extreme-xos:quoted-string;
                tailf:info
                  "Password is Encrypted";
                type string {
                  tailf:info
                    "<encrypted_secret>;;encrypted secret string";
                }
                tailf:cli-no-value-on-delete;
                tailf:cli-no-name-on-delete;
              }
              tailf:cli-no-name-on-delete;
            }
          }
          leaf nas-ip {
            tailf:cli-no-value-on-delete;
            tailf:cli-no-name-on-delete;
            tailf:info
              "Configure Network Access Server (NAS) IP Address requirement";
            type enumeration {
              enum "ignore" {
                tailf:info
                  "Ignore Network Access Server (NAS) IP Address requirement";
              }
              enum "require" {
                tailf:info
                  "Require Network Access Server (NAS) IP Address (Default)";
              }
            }
            default "require";
          }
        }
        container mgmt-access {
          tailf:info
            "RADIUS authentication for management access";
          uses radius-timeout-grouping;
        }
        uses radius-timeout-grouping;
      }
      container netlogin {
        tailf:info
          "Configure Network Login specific settings";
        tailf:cli-diff-dependency "/extreme-xos:enable/netlogin/ports" {
          tailf:xpath-root 3;
        }
        container add {
          tailf:info
            "Add a MAC-list entry";
          list mac-list {
            tailf:cli-delete-when-empty;
            tailf:cli-compact-syntax;
            tailf:cli-suppress-mode;
            tailf:info
              "Configure a Network Login MAC-list entry";
            key "mac mask";
            leaf mac {
              type string {
                tailf:info
                  "<mac>;;MAC address to as to the MAC-list";
              }
            }
            leaf mask {
              type uint8 {
                tailf:info
                  "<mask>;;Number of bits used for the mask";
              }
            }
            leaf ports {
              tailf:info
                "Physical ports";
              tailf:cli-no-value-on-delete;
              tailf:cli-no-name-on-delete;
              type string {
                tailf:info
                  "<portlist>;;List of ports separated by comma";
              }
            }
          }
        }
        container mac {
          tailf:info
            "Configure Network Login settings specific to MAC";
          container authentication {
            tailf:info
              "Configure order of authentication methods to use";
            container database-order {
              tailf:info
                "Configure order of authentication database methods to use";
              tailf:cli-compact-syntax;
              leaf local {
                tailf:cli-no-name-on-delete;
                tailf:info
                  "Local user database authentication method";
                type empty;
              }
              leaf radius {
                tailf:cli-no-name-on-delete;
                tailf:info
                  "Radius Server authentication method";
                type empty;
              }
            }
          }
          list ports {
            tailf:info
              "port list";
            tailf:cli-suppress-mode;
            tailf:cli-delete-when-empty;
            tailf:cli-range-list-syntax;
            key "id";
            leaf id {
              type union {
                type uint32 {
                  tailf:info
                    "<port_list>;;Port list";
                }
                type enumeration {
                  enum "all" {
                    tailf:info
                      "all";
                  }
                }
              }
            }
            container timers {
              tailf:info
                "Configure MAC protocol timers";
              leaf delay {
                extreme-xos:replace-delete-output "un(.*) :: $1 0";
                tailf:cli-no-value-on-delete;
                tailf:info
                  "Delay MAC authentication to wait for 802.1x or web-based authentication to take place";
                type uint8 {
                  tailf:info
                    "<delay>;;MAC authentication delay in seconds (0..120 sec) (default 0 second)";
                }
                default "0";
              }
              container reauth-wrap {
                tailf:cli-drop-node-name;
                tailf:cli-compact-syntax;
                extreme-xos:replace-delete-output "un(.* reauth-period).*(reauthentication).* :: $1 3600 $2 off";
                leaf reauth-period {
                  tailf:info
                    "Configure MAC reauthentication period";
                  type uint32 {
                    tailf:info
                      "<reauth_period>;;Reauth period (30..86400 sec) (Default 3600 sec)";
                  }
                  default "3600";
                }
                leaf reauthentication {
                  tailf:info
                    "Configure MAC reauthentication";
                  type enumeration {
                    enum "off" {
                      tailf:info
                        "MAC reauthentication is disabled (default)";
                    }
                    enum "on" {
                      tailf:info
                        "MAC reauthentication is enabled";
                    }
                  }
                  default "off";
                }
              }
            }
          }
        }
        container dot1x {
          tailf:info
            "Configure Network Login settings specific to 802.1X";
          list ports {
            tailf:info
              "Specify list of ports to configure 802.1X protocol timers";
            tailf:cli-suppress-mode;
            tailf:cli-delete-when-empty;
            tailf:cli-range-list-syntax;
            key "id";
            leaf id {
              type union {
                type uint32 {
                  tailf:info
                    "<port_list>;;Port list";
                }
                type enumeration {
                  enum "all" {
                    tailf:info
                      "all";
                  }
                }
              }
            }
            container timers {
              tailf:info
                "Configure 802.1X protocol timers";
              extreme-xos:replace-delete-output "un(.* server-timeout).*(quiet-period).*(supp-resp-timeout).* :: $1 30 $2 60 $3 30";
              tailf:cli-compact-syntax;
              leaf server-timeout {
                tailf:info
                  "Configure RADIUS server timeout for 802.1X";
                type uint16 {
                  tailf:info
                    "<server_timeout>;;RADIUS server timeout (1..120 sec)";
                }
                default "30";
              }
              leaf quiet-period {
                tailf:info
                  "Configure 802.1X quiet period";
                type uint16 {
                  tailf:info
                    "<quiet_period>;;Quiet period (0..65535 sec)";
                }
                default "60";
              }
              leaf supp-resp-timeout {
                tailf:info
                  "Configure supplicant response timeout";
                type uint16 {
                  tailf:info
                    "<supp_resp_timeout>;;Supplicant response timeout (1..120 sec)";
                }
                default "30";
              }
            }
          }
        }
        list ports {
          extreme-xos:trim-delete-if-match "unconfigure netlogin ports \\S+";
          tailf:info
            "Specify ports to add";
          tailf:cli-suppress-mode;
          tailf:cli-range-list-syntax;
          tailf:cli-delete-when-empty;
          key "id";
          leaf id {
            type union {
              type uint32 {
                tailf:info
                  "<port_list>;;Port list";
              }
              type enumeration {
                enum "all" {
                  tailf:info
                    "all";
                }
              }
            }
          }
          leaf mode {
            tailf:cli-no-name-on-delete;
            tailf:cli-no-value-on-delete;
            tailf:info
              "Configure port operation mode";
            type enumeration {
              enum "mac-based-vlans" {
                tailf:info
                  "Allow more than one untagged VLAN";
              }
              enum "port-based-vlans" {
                tailf:info
                  "Allow only one untagged VLAN";
              }
            }
          }
        }
        container authentication {
          tailf:info
            "Configure Network Login client authentication settings";
          leaf protocol-order {
            tailf:cli-diff-set-after "/extreme-xos:enable/policy" {
              tailf:xpath-root 3;
            }
            tailf:cli-no-value-on-delete;
            extreme-xos:replace-delete-output "un(.*) :: $1 dot1x web-based mac cep";
            tailf:info
              "Configure order of authentication protocol methods to use";
            tailf:cli-multi-value;
            type string;
          }
        }
        leaf vlan {
          tailf:cli-no-value-on-delete;
          tailf:non-strict-leafref {
            path "/ncs:devices/ncs:device/ncs:config/extreme-xos:create/vlan/id" {
              tailf:xpath-root 3;
            }
          }
          tailf:cli-diff-set-after "/extreme-xos:create/vlan" {
            tailf:xpath-root 3;
            tailf:cli-when-target-create;
          }
          tailf:cli-diff-delete-before "/extreme-xos:create/vlan" {
            tailf:xpath-root 3;
            tailf:cli-when-target-delete;
          }
          tailf:info
            "VLAN";
          type string {
            tailf:info
              "<vlan_name>;;VLAN name";
          }
        }
      }
      container policy {
        tailf:info
          "Policy Classification";
        leaf rule-model {
          tailf:cli-diff-delete-after "/extreme-xos:enable/policy" {
            tailf:xpath-root 3;
            tailf:cli-when-target-delete;
          }
          tailf:cli-diff-set-before "/extreme-xos:enable/policy" {
            tailf:xpath-root 3;
            tailf:cli-when-target-set;
          }
          extreme-xos:replace-delete-output "un(.*) :: $1 hierarchical";
          tailf:cli-no-value-on-delete;
          tailf:info
            "Select a rule model for configuring and ordering policy based rules";
          type enumeration {
            enum "access-list" {
              tailf:info
                "Access-list rule model allows multiple match criteria
                 per rule along with assignable rule ordering within an access-list.";
            }
            enum "hierarchical" {
              tailf:info
                "Hierarchical rule model allows one match criteria per rule
                 and uses the rule type to assign its precedence (Default).";
            }
          }
          default "hierarchical";
        }
        container slices {
          tailf:info
            "Configure Lookup Stage TCAM resources";
          leaf tci-overwrite {
            tailf:cli-diff-set-before "/extreme-xos:enable/policy" {
              tailf:xpath-root 3;
              tailf:cli-when-target-set;
            }
            extreme-xos:replace-delete-output "un(.*) :: $1 4";
            tailf:cli-no-value-on-delete;
            tailf:info
              "Configure Lookup Stage TCAM resources used by profile with tci-overwrite enabled";
            type uint8 {
              tailf:info
                "<slices>;;Number of slices between 0 and 4 (Default 4)";
            }
            default "4";
          }
          leaf shared {
            tailf:cli-diff-delete-before "../tci-overwrite" {
              tailf:xpath-root 3;
              tailf:cli-when-target-delete;
            }
            tailf:cli-diff-set-before "/extreme-xos:enable/policy" {
              tailf:xpath-root 3;
              tailf:cli-when-target-set;
            }
            extreme-xos:replace-delete-output "un(.*) :: $1 0";
            tailf:cli-no-value-on-delete;
            tailf:info
              "Configure Lookup Stage TCAM resources";
            type uint8 {
              tailf:info
                "<shared>;;Shared slice value - (0-4)";
            }
            default "0";
          }
        }
        container maptable {
          tailf:info
            "Set VLAN ID - Policy Profile mappings table";
          leaf response {
            tailf:cli-no-value-on-delete;
            tailf:info
              "Indicates which attributes to use from RADIUS response";
            type enumeration {
              enum "both" {
                tailf:info
                  "Apply both attributes";
              }
              enum "policy" {
                tailf:info
                  "Apply the filter-id attribute";
              }
              enum "tunnel" {
                tailf:info
                  "Apply the vlan-tunnel attribute";
              }
            }
          }
        }
        container vlanauthorization {
          tailf:info
            "Configure VLAN Authorization specific settings";
          leaf enable {
            tailf:cli-no-name-on-delete;
            extreme-xos:replace-delete-output "un(.*) :: $1 disable";
            tailf:info
              "Enable VLAN Authorization";
            type empty;
          }
        }
        list profile {
          tailf:info
            "Set current policy profile";
          tailf:cli-compact-syntax;
          tailf:cli-suppress-mode;
          key "index";
          leaf index {
            type uint8 {
              tailf:info
                "<profile_index>;;Policy ID [1-63]";
            }
          }
          leaf name {
            tailf:cli-no-value-on-delete;
            tailf:cli-no-name-on-delete;
            tailf:info
              "Policy profile name";
            type string {
              tailf:info
                "<name>;;Profile name string 1-64 characters";
            }
          }
          leaf access-list {
            tailf:cli-no-value-on-delete;
            tailf:cli-no-name-on-delete;
            tailf:info
              "Assign an access-list to this profile";
            type string {
              tailf:info
                "<list_name>;;Existing Access-list name to assign to this profile";
            }
          }
          leaf pvid-status {
            tailf:cli-no-value-on-delete;
            tailf:cli-no-name-on-delete;
            tailf:info
              "PVid status - enable / disable";
            type enumeration {
              enum "enable";
              enum "disable";
            }
          }
          leaf pvid {
            tailf:cli-no-value-on-delete;
            tailf:cli-no-name-on-delete;
            tailf:info
              "PVid value - (0-4095)";
            type uint16 {
              tailf:info
                "<pvid>;;PVid value - (0-4095)";
            }
          }
          leaf web-redirect {
            tailf:cli-no-value-on-delete;
            tailf:cli-no-name-on-delete;
            tailf:info
              "Web Redirect class index value - (0-10)";
            type uint16 {
              tailf:info
                "<web_redir_index>;;Web Redirect class index value - (0-10)(Defaults to 0 which is disabled)";
            }
          }
        }
        container captive-portal {
          tailf:info
            "Configure a Captive Portal that uses HTTP redirection to force a client's web browser to be redirected to a URL";
          leaf-list listening {
            tailf:cli-list-syntax;
            tailf:cli-remove-before-change;
            tailf:info
              "Configure Captive Portal HTTP listening ports (up to 3 L4 ports)";
            type string {
              tailf:info
                "<socket_list>;;List of up to 3 sockets on which to listen (1-65535) comma separated (eg.. 80,8080,2000)";
            }
          }
          list web-redirect {
            tailf:info
              "Configure Web Redirect";
            tailf:cli-suppress-mode;
            tailf:cli-compact-syntax;
            key "index server";
            leaf index {
              type uint8 {
                tailf:info
                  "<redirect_index>;;Configure a Web Redirect index (1-10)";
              }
            }
            leaf server {
              tailf:cli-expose-key-name;
              tailf:info
                "Configure a Server for the Web Redirect Index";
              type uint8 {
                tailf:info
                  "<server_id>;;Server id to use (1-2)";
              }
            }
            leaf url {
              tailf:cli-no-value-on-delete;
              tailf:cli-no-name-on-delete;
              tailf:info
                "Captive Portal Server absolute URL";
              type string {
                tailf:info
                  "<redirect_url>;;HTTP or HTTPS URL that user is redirected to (http://<IPv4Address or Hostname>:<L4Port>/<Path>)";
              }
            }
            leaf status {
              tailf:cli-no-value-on-delete;
              tailf:cli-drop-node-name;
              type enumeration {
                enum "enable" {
                  tailf:info
                    "Captive Portal Server status - enable / disable (Default disable)";
                }
                enum "disable";
              }
            }
          }
        }
      }
      list stpd {
        tailf:info
          "STP domain/STP global configuration";
        tailf:cli-compact-syntax;
        tailf:cli-suppress-mode;
        tailf:cli-delete-when-empty;
        tailf:cli-diff-create-after "/extreme-xos:enable/stpd" {
          tailf:xpath-root 3;
          tailf:cli-when-target-create;
        }
        tailf:cli-diff-delete-before "/extreme-xos:enable/stpd" {
          tailf:xpath-root 3;
          tailf:cli-when-target-delete;
        }
        extreme-xos:trim-delete-if-match "unconfigure.*mode dot1d.*";
        key "name";
        leaf name {
          type string {
            tailf:info
              "<stpd_name>;;STP domain name";
          }
        }
        container ports {
          tailf:info
            "Ports in this STP domain to configure";
          container edge-safeguard {
            tailf:info
              "Edge port safe guard mode (transmit BPDUs)";
            uses ports-enable-grouping;
          }
          container bpdu-restrict {
            tailf:info
              "Disable port as soon as BPDU is received";
            uses ports-enable-grouping;
          }
          list link-type {
            tailf:info
              "802.1w port mode";
            tailf:cli-suppress-mode;
            tailf:cli-compact-syntax;
            tailf:cli-range-list-syntax;
            tailf:cli-diff-create-after "/extreme-xos:create/stpd" {
              tailf:xpath-root 3;
              tailf:cli-when-target-create;
            }
            tailf:cli-diff-delete-before "/extreme-xos:create/stpd" {
              tailf:xpath-root 3;
              tailf:cli-when-target-delete;
            }
            tailf:cli-diff-create-after "/extreme-xos:enable/stpd" {
              tailf:xpath-root 3;
              tailf:cli-when-target-create;
            }
            tailf:cli-diff-delete-before "/extreme-xos:enable/stpd" {
              tailf:xpath-root 3;
              tailf:cli-when-target-delete;
            }
            key "ports";
            leaf ports {
              type union {
                type uint32 {
                  tailf:info
                    "<port_list>;;List of ports to configure";
                }
                type enumeration {
                  enum "all" {
                    tailf:info
                      "Configure all ports in the system";
                  }
                }
              }
            }
            leaf edge {
              tailf:cli-prefix-key;
              tailf:info
                "edge mode";
              tailf:cli-no-name-on-delete;
              type empty;
            }
          }
        }
        list add {
          tailf:info
            "Add ports in a vlan to a STP domain";
          tailf:cli-compact-syntax;
          tailf:cli-suppress-mode;
          tailf:cli-delete-when-empty;
          key "vlan";
          leaf vlan {
            type string {
              tailf:info
                "VLAN";
            }
            tailf:cli-expose-key-name;
          }
          leaf-list ports {
            tailf:cli-diff-set-after "/extreme-xos:create/vlan" {
              tailf:xpath-root 3;
              tailf:cli-when-target-create;
            }
            tailf:cli-diff-delete-before "/extreme-xos:create/vlan" {
              tailf:xpath-root 3;
              tailf:cli-when-target-delete;
            }
            tailf:info
              "Ports in this VLAN to add";
            tailf:cli-range-list-syntax;
            type uint32 {
              tailf:info
                "<port_list>;;Ports in this VLAN to add";
            }
          }
          leaf dot1d {
            tailf:cli-no-name-on-delete;
            tailf:info
              "802.1d mode";
            type empty;
          }
        }
      }
      container cdp {
        tailf:info
          "Cisco Discovery Protocol (CDP)";
        list voip-vlan {
          extreme-xos:replace-delete-output "un(configure cdp voip-vlan) \\S+ (.*) :: $1 none $2";
          tailf:info
            "VLAN information for Voice traffic received from IP phone.";
          tailf:cli-compact-syntax;
          tailf:cli-suppress-mode;
          tailf:cli-delete-when-empty;
          tailf:cli-diff-set-after "/extreme-xos:create/vlan" {
            tailf:xpath-root 3;
            tailf:cli-when-target-create;
          }
          tailf:cli-diff-delete-before "/extreme-xos:create/vlan" {
            tailf:xpath-root 3;
            tailf:cli-when-target-delete;
          }
          key "vlan_name";
          leaf vlan_name {
            type string {
              tailf:info
                "<vlan_name>;;VLAN name";
            }
          }
          uses port-list-grouping;
        }
      }
      container lldp {
        tailf:info
          "Configure LLDP specific settings";
        list ports {
          tailf:cli-diff-set-after "/extreme-xos:create/vlan" {
            tailf:xpath-root 3;
            tailf:cli-when-target-create;
          }
          tailf:cli-diff-delete-before "/extreme-xos:create/vlan" {
            tailf:xpath-root 3;
            tailf:cli-when-target-delete;
          }
          tailf:info
            "Specify ports to configure";
          tailf:cli-suppress-mode;
          tailf:cli-compact-syntax;
          tailf:cli-range-list-syntax;
          key "id";
          leaf id {
            type union {
              type uint32 {
                tailf:info
                  "<port_list>;;List of ports to configure";
              }
              type enumeration {
                enum "all" {
                  tailf:info
                    "Configure all ports in the system";
                }
              }
            }
          }
          container advertise {
            tailf:cli-no-name-on-delete;
            tailf:info
              "Specifies to send the TLV to neighbors";
            leaf port-description {
              tailf:cli-no-name-on-delete;
              tailf:info
                "Advertise the LLDP Port Description TLV";
              type empty;
            }
            leaf system-capabilities {
              tailf:cli-no-name-on-delete;
              tailf:info
                "Advertise the LLDP System Capabilities TLV";
              type empty;
            }
            leaf management-address {
              tailf:cli-no-name-on-delete;
              tailf:info
                "Advertise the LLDP Management Address TLV";
              type empty;
            }
          }
        }
      }
      container inline-power {
        tailf:info
          "Inline-Power";
        container detection {
          tailf:info
            "PoE device detection mode";
          list portlist {
            tailf:cli-drop-node-name;
            tailf:cli-diff-set-after "/extreme-xos:create/vlan" {
              tailf:xpath-root 3;
              tailf:cli-when-target-create;
            }
            tailf:cli-diff-delete-before "/extreme-xos:create/vlan" {
              tailf:xpath-root 3;
              tailf:cli-when-target-delete;
            }
            tailf:cli-suppress-mode;
            tailf:cli-compact-syntax;
            tailf:cli-range-list-syntax;
            key "ports";
            leaf ports {
              tailf:info
                "port";
              tailf:cli-expose-key-name;
              type union {
                type uint32 {
                  tailf:info
                    "<port_list>;;List of ports to configure";
                }
                type enumeration {
                  enum "all" {
                    tailf:info
                      "Configure all ports in the system";
                  }
                }
              }
            }
            leaf "legacy-and-802.3af" {
              tailf:cli-no-name-on-delete;
              tailf:cli-no-value-on-delete;
              tailf:cli-prefix-key;
              tailf:info
                "Capacitive and IEEE 802.3af detection (default for VPEX V400 products)";
              type enumeration {
                enum "2-point" {
                  tailf:info
                    "2-point detection (for extended detection signature range)";
                }
                enum "4-point" {
                  tailf:info
                    "4-point detection (default)";
                }
              }
            }
          }
        }
      }
    }
    container enable {
      tailf:ncs-device-type "cli-ned";
      tailf:display-when "not(../../ncs:module) or ../../ncs:module[ncs:name='tailf-ned-extreme-xos']";
      tailf:info
        "Enable running system setting";
      extreme-xos:no-to-disable;
      container snmp {
        tailf:info
          "Enable SNMP";
        container access {
          tailf:cli-display-separated;
          tailf:info
            "Enable SNMP-v1v2c and SNMPv3 access";
          presence "true";
          leaf snmp-v1v2c {
            tailf:info
              "Enable SNMPv1 and SNMPv2c access";
            type empty;
          }
          leaf snmpv3 {
            tailf:info
              "Enable SNMPv3 access";
            type empty;
          }
        }
        container traps {
          tailf:info
            "Configure SNMP Trap generation settings";
          leaf fdb {
            tailf:info
              "Configure FDB related traps";
            type enumeration {
              enum "mac-tracking" {
                tailf:info
                  "Configure MAC address tracking specific traps";
              }
            }
          }
          container configuration {
            tailf:info
              "Traps for switch configuration";
            leaf change {
              tailf:info
                "Generate trap when configuration is changed (Default disabled)";
              type empty;
            }
            leaf save {
              tailf:info
                "Generate trap when configuration is saved (Default disabled)";
              type empty;
            }
          }
        }
      }
      leaf ssh2 {
        tailf:info
          "allow incoming ssh connections";
        type empty;
      }
      leaf cli-config-logging {
        tailf:info
          "CLI command logging";
        type empty;
      }
      leaf tacacs {
        tailf:info
          "TACACS+ Client";
        type empty;
      }
      leaf tacacs-accounting {
        tailf:info
          "TACACS+ accounting";
        type empty;
      }
      leaf tacacs-authorization {
        tailf:info
          "TACACS+ Client Cli Authorization";
        type empty;
      }
      leaf sntp-client {
        tailf:info
          "Enable SNTP client";
        type empty;
      }
      container log {
        tailf:info
          "Configure log service";
        leaf debug-mode {
          tailf:info
            "Debug-Mode";
          type empty;
        }
        container target {
          tailf:info
            "Target to enable or disable";
          list syslog {
            tailf:cli-diff-create-after "/extreme-xos:create/vr" {
              tailf:xpath-root 3;
              tailf:cli-when-target-create;
            }
            tailf:cli-diff-delete-before "/extreme-xos:create/vr" {
              tailf:xpath-root 3;
              tailf:cli-when-target-delete;
            }
            tailf:info
              "Remote syslog target";
            tailf:cli-compact-syntax;
            tailf:cli-suppress-mode;
            key "ipPort vr local";
            leaf ipPort {
              type string {
                tailf:info
                  "<ipPort>;;Remote syslog server IPv4 address : UDP Port";
              }
            }
            leaf vr {
              tailf:cli-expose-key-name;
              tailf:info
                "Virtual router ID";
              type string {
                tailf:info
                  "<vr_name>;;Virtual router ID";
              }
            }
            leaf local {
              tailf:cli-drop-node-name;
              type string {
                tailf:info
                  "<local>;;Remote syslog server facility";
              }
            }
          }
          leaf-list upm {
            tailf:info
              "Sending messages to UPM as event";
            tailf:cli-list-syntax;
            tailf:cli-diff-create-after "/extreme-xos:create/log/target/upm" {
              tailf:xpath-root 3;
              tailf:cli-when-target-create;
            }
            tailf:cli-diff-delete-before "/extreme-xos:create/log/target/upm" {
              tailf:xpath-root 3;
              tailf:cli-when-target-delete;
            }
            tailf:cli-diff-modify-before "/extreme-xos:create/log/target/upm" {
              tailf:xpath-root 3;
              tailf:cli-when-target-modify;
            }
            type string {
              tailf:info
                "<upm_profile_name>;;UPM Profile Name";
            }
          }
        }
      }
      container cli {
        tailf:info
          "Command line interface (CLI)";
        leaf config-logging {
          tailf:info
            "CLI command logging";
          type empty;
        }
      }
      container loopback-mode {
        tailf:info
          "loopback";
        list vlan {
          tailf:cli-diff-set-after "/extreme-xos:create/vlan" {
            tailf:xpath-root 3;
            tailf:cli-when-target-create;
          }
          tailf:cli-diff-delete-before "/extreme-xos:create/vlan" {
            tailf:xpath-root 3;
            tailf:cli-when-target-delete;
          }
          tailf:info
            "VLAN";
          tailf:cli-compact-syntax;
          tailf:cli-suppress-mode;
          key "id";
          leaf id {
            type string {
              tailf:info
                "<vlan_name>;;VLAN Name";
            }
          }
        }
      }
      container ipforwarding {
        tailf:info
          "IP forwarding";
        list vlan {
          tailf:info
            "VLAN";
          tailf:cli-compact-syntax;
          tailf:cli-suppress-mode;
          tailf:cli-diff-set-after "/extreme-xos:create/vlan" {
            tailf:xpath-root 3;
            tailf:cli-when-target-create;
          }
          tailf:cli-diff-delete-before "/extreme-xos:create/vlan" {
            tailf:xpath-root 3;
            tailf:cli-when-target-delete;
          }
          tailf:cli-diff-set-after "/extreme-xos:configure/vlan/ipaddress/ipaddress" {
            tailf:xpath-root 3;
            tailf:cli-when-target-create;
          }
          tailf:cli-diff-delete-before "/extreme-xos:configure/vlan/ipaddress/ipaddress" {
            tailf:xpath-root 3;
            tailf:cli-when-target-delete;
          }
          key "id";
          leaf id {
            type string {
              tailf:info
                "<vlan_name>;;VLAN Name";
            }
          }
        }
      }
      container diffserv {
        tailf:info
          "diffserv";
        uses exam-grouping;
      }
      container radius {
        tailf:info
          "RADIUS Client";
        leaf netlogin {
          tailf:info
            "RADIUS authentication for netlogin access";
          type empty;
        }
        leaf dynamic-authorization {
          tailf:info
            "RADIUS Dynamic Authorization";
          type empty;
        }
      }
      list stpd {
        tailf:info
          "STP domain";
        tailf:cli-compact-syntax;
        tailf:cli-suppress-mode;
        tailf:cli-delete-when-empty;
        tailf:cli-diff-set-after "/extreme-xos:create/stpd" {
          tailf:xpath-root 3;
          tailf:cli-when-target-create;
        }
        tailf:cli-diff-delete-before "/extreme-xos:create/stpd" {
          tailf:xpath-root 3;
          tailf:cli-when-target-delete;
        }
        key "name";
        leaf name {
          type string {
            tailf:info
              "<stpd_name>;;STP domain name";
          }
        }
        container auto-bind {
          tailf:info
            "Auto-bind feature for dynamic port changes";
          // NCS expand uses statement
          leaf-list vlan {
            tailf:cli-list-syntax;
            tailf:non-strict-leafref {
              path "/ncs:devices/ncs:device/ncs:config/extreme-xos:create/vlan/id" {
                tailf:xpath-root 3;
              }
            }
            tailf:cli-diff-set-after "/extreme-xos:create/vlan" {
              tailf:xpath-root 3;
              tailf:cli-when-target-create;
            }
            tailf:cli-diff-delete-before "/extreme-xos:create/vlan" {
              tailf:xpath-root 3;
              tailf:cli-when-target-delete;
            }
            tailf:info
              "VLAN";
            type string {
              tailf:info
                "<vlan_name>;;VLAN name";
            }
            tailf:cli-diff-delete-after "/extreme-xos:configure/stpd/ports" {
              tailf:xpath-root 3;
            }
          }
        }
      }
      container netlogin {
        tailf:info
          "Network Login related commands";
        list ports {
          tailf:cli-diff-set-after "/extreme-xos:create/vlan" {
            tailf:xpath-root 3;
            tailf:cli-when-target-create;
          }
          tailf:cli-diff-delete-before "/extreme-xos:create/vlan" {
            tailf:xpath-root 3;
            tailf:cli-when-target-delete;
          }
          tailf:info
            "port list";
          tailf:cli-suppress-mode;
          tailf:cli-delete-when-empty;
          tailf:cli-range-list-syntax;
          key "id";
          leaf id {
            type union {
              type uint32 {
                tailf:info
                  "<port_list>;;Port list";
              }
              type enumeration {
                enum "all" {
                  tailf:info
                    "all";
                }
              }
            }
          }
          uses netlogin-authprotocol-grouping;
        }
        container dot1x-max {
          tailf:cli-drop-node-name;
          tailf:cli-compact-syntax;
          // NCS expand uses statement
          leaf dot1x {
            tailf:info
              "Configure the 802.1x authentication protocol";
            type empty;
            tailf:cli-diff-set-after "/extreme-xos:configure/netlogin/vlan" {
              tailf:xpath-root 3;
              tailf:cli-when-target-create;
            }
            tailf:cli-diff-delete-before "/extreme-xos:configure/netlogin/vlan" {
              tailf:xpath-root 3;
              tailf:cli-when-target-delete;
            }
          }
          leaf mac {
            tailf:info
              "Configure the MAC-based authentication protocol";
            type empty;
            tailf:cli-diff-set-after "/extreme-xos:configure/netlogin/vlan" {
              tailf:xpath-root 3;
              tailf:cli-when-target-create;
            }
            tailf:cli-diff-delete-before "/extreme-xos:configure/netlogin/vlan" {
              tailf:xpath-root 3;
              tailf:cli-when-target-delete;
            }
          }
          leaf web-based {
            tailf:info
              "Configure the web-based authentication protocol";
            type empty;
            tailf:cli-diff-set-after "/extreme-xos:configure/netlogin/vlan" {
              tailf:xpath-root 3;
              tailf:cli-when-target-create;
            }
            tailf:cli-diff-delete-before "/extreme-xos:configure/netlogin/vlan" {
              tailf:xpath-root 3;
              tailf:cli-when-target-delete;
            }
          }
        }
      }
      leaf policy {
        tailf:info
          "Policy Classification";
        type empty;
      }
      container cdp {
        tailf:info
          "Cisco Discovery Protocol (CDP)";
        uses port-list-grouping;
      }
      container ip-security {
        tailf:info
          "IP Security";
        container dhcp-snooping {
          tailf:info
            "DHCP Snooping";
          list vlan {
            tailf:cli-diff-set-after "/extreme-xos:create/vlan" {
              tailf:xpath-root 3;
              tailf:cli-when-target-create;
            }
            tailf:cli-diff-delete-before "/extreme-xos:create/vlan" {
              tailf:xpath-root 3;
              tailf:cli-when-target-delete;
            }
            tailf:cli-diff-set-after "/extreme-xos:configure/vlan" {
              tailf:xpath-root 3;
              tailf:cli-when-target-create;
            }
            tailf:cli-diff-delete-before "/extreme-xos:configure/vlan" {
              tailf:xpath-root 3;
              tailf:cli-when-target-delete;
            }
            tailf:info
              "VLAN";
            tailf:cli-compact-syntax;
            tailf:cli-suppress-mode;
            tailf:cli-delete-when-empty;
            key "id";
            leaf id {
              type string {
                tailf:info
                  "<vlan_name>;;VLAN Name";
              }
            }
            list ports {
              tailf:cli-diff-set-after "/extreme-xos:create/vlan" {
                tailf:xpath-root 3;
                tailf:cli-when-target-create;
              }
              tailf:cli-diff-delete-before "/extreme-xos:create/vlan" {
                tailf:xpath-root 3;
                tailf:cli-when-target-delete;
              }
              tailf:cli-diff-set-after "/extreme-xos:configure/vlan/add/ports" {
                tailf:xpath-root 3;
                tailf:cli-when-target-create;
              }
              tailf:cli-diff-delete-before "/extreme-xos:configure/vlan/add/ports" {
                tailf:xpath-root 3;
                tailf:cli-when-target-delete;
              }
              tailf:cli-diff-delete-before "/extreme-xos:configure/vlan/add/ports" {
                tailf:xpath-root 3;
                tailf:cli-when-target-create;
              }
              tailf:info
                "port list";
              tailf:cli-suppress-mode;
              tailf:cli-compact-syntax;
              tailf:cli-range-list-syntax;
              key "id";
              leaf id {
                type union {
                  type uint32 {
                    tailf:info
                      "<port_list>;;Port list";
                  }
                  type enumeration {
                    enum "all" {
                      tailf:info
                        "all";
                    }
                  }
                }
              }
              leaf violation-action {
                tailf:cli-no-name-on-delete;
                tailf:cli-no-value-on-delete;
                tailf:info
                  "Action to take on DHCP violation";
                type enumeration {
                  enum "drop-packet" {
                    tailf:info
                      "Drop the violating DHCP packet";
                  }
                  enum "none" {
                    tailf:info
                      "Take no action";
                  }
                }
              }
            }
          }
        }
      }
    }
    container disable {
      tailf:ncs-device-type "cli-ned";
      tailf:display-when "not(../../ncs:module) or ../../ncs:module[ncs:name='tailf-ned-extreme-xos']";
      tailf:info
        "Enable running system setting";
      extreme-xos:no-to-disable;
      leaf telnet {
        type empty;
        tailf:info
          "allow incoming telnet connections";
      }
      list stpd {
        tailf:info
          "STP domain";
        tailf:cli-suppress-mode;
        key "stpd_name";
        leaf stpd_name {
          type string {
            tailf:info
              "<stpd_name>;;STP domain name";
          }
        }
      }
      container snmp {
        tailf:info
          "Disable SNMP";
        container traps {
          tailf:info
            "Configure SNMP Trap generation settings";
          container port-up-down {
            tailf:info
              "Configure port-up-down specific traps";
            leaf-list port {
              tailf:info
                "Specify ports to configure";
              tailf:cli-list-syntax;
              tailf:cli-range-list-syntax;
              type uint32 {
                tailf:info
                  "<port_list>;;Port List to configure";
              }
            }
          }
        }
      }
      container dot1p {
        tailf:info
          "dot1p";
        uses exam-grouping;
      }
      container edp {
        tailf:info
          "EDP (Extreme Discovery Protocol)";
        uses port-list-grouping;
      }
    }
  }
  augment "/ncs:devices/ncs:template/ncs:ned-id/ncs:config" {
    container create {
      extreme-xos:delete-with "delete";
      list account {
        // NCS patched for predictable order
        ordered-by user;
        tailf:cli-suppress-mode;
        key "account-name";
        leaf account-name {
          type string;
        }
        leaf account-type {
          tailf:cli-drop-node-name;
          type string;
        }
        leaf encrypted {
          cli:secret "encrypted <SECRET>" {
            cli:arguments "always-encrypted";
          }
          extreme-xos:accounts-password;
          type string;
        }
        leaf old-password {
          type string;
          tailf:cli-drop-node-name;
        }
      }
      list access-list {
        // NCS patched for predictable order
        ordered-by user;
        extreme-xos:redeploy-access-profile-at-acl-modify;
        tailf:cli-suppress-mode;
        key "dynamic-rule";
        leaf dynamic-rule {
          type string;
        }
        leaf conditions {
          tailf:cli-drop-node-name;
          type string;
        }
        leaf actions {
          tailf:cli-drop-node-name;
          type string;
        }
        leaf application {
          type string;
        }
      }
      list vlan {
        // NCS patched for predictable order
        ordered-by user;
        // NCS drop tailf-common:cli-diff-create-after statement
        // NCS drop tailf-common:cli-diff-delete-before statement
        tailf:cli-suppress-mode;
        key "id";
        leaf id {
          type string;
        }
        leaf vr {
          type string;
        }
      }
      list vr {
        // NCS patched for predictable order
        ordered-by user;
        tailf:cli-suppress-mode;
        key "id";
        leaf id {
          type string;
        }
      }
      leaf-list qosprofile {
        // NCS patched for predictable order
        ordered-by user;
        type string;
      }
      container log {
        leaf-list filter {
          // NCS patched for predictable order
          ordered-by user;
          type string;
        }
        container target {
          leaf-list upm {
            // NCS patched for predictable order
            ordered-by user;
            // NCS drop tailf-common:cli-diff-delete-before statement
            // NCS drop tailf-common:cli-diff-modify-before statement
            // NCS drop tailf-common:cli-diff-delete-before statement
            // NCS drop tailf-common:cli-diff-create-after statement
            // NCS drop tailf-common:cli-diff-delete-before statement
            // NCS drop tailf-common:cli-diff-create-after statement
            type string;
          }
        }
      }
      container upm {
        list profile {
          // NCS patched for predictable order
          ordered-by user;
          extreme-xos:remove-before-change;
          key "name";
          leaf name {
            type string;
          }
          leaf commands {
            tailf:cli-drop-node-name;
            extreme-xos:upm-list-out;
            type string;
          }
        }
      }
      list stpd {
        // NCS patched for predictable order
        ordered-by user;
        tailf:cli-suppress-mode;
        key "name";
        leaf name {
          type string;
        }
      }
    }
    container configure {
      extreme-xos:delete-with "unconfigure";
      extreme-xos:trim-delete-if-match "unconfigure vlan \\S* tag";
      extreme-xos:trim-delete-if-match "unconfigure timezone.*";
      extreme-xos:trim-delete-if-match "unconfigure account.*";
      extreme-xos:trim-delete-if-match "unconfigure log target upm.*";
      list access-list {
        // NCS patched for predictable order
        ordered-by user;
        // NCS drop tailf-common:cli-diff-create-after statement
        // NCS drop tailf-common:cli-diff-delete-before statement
        tailf:cli-suppress-mode;
        key "aclname";
        leaf aclname {
          type string;
        }
        leaf any {
          type string;
        }
      }
      container snmp {
        container access-profile {
          list add {
            // NCS patched for predictable order
            ordered-by user;
            // NCS drop tailf-common:cli-diff-create-after statement
            // NCS drop tailf-common:cli-diff-delete-before statement
            tailf:cli-suppress-mode;
            key "rule";
            leaf rule {
              type string;
            }
            leaf condition {
              tailf:cli-drop-node-name;
              type string;
            }
            leaf previous_rule {
              tailf:cli-drop-node-name;
              type string;
            }
          }
        }
        leaf sysContact {
          extreme-xos:replace-delete-output "unconfigure snmp sysContact :: configure snmp sysContact \"support@extremenetworks.com, +1 888 257 3000\"";
          type string;
          // NCS drop default statement
        }
        leaf sysLocation {
          extreme-xos:replace-delete-output "unconfigure snmp sysLocation :: configure snmp sysLocation \"NO LOCATION PROVIDED\"";
          type string;
          // NCS drop default statement
        }
        leaf sysName {
          extreme-xos:replace-delete-output "unconfigure snmp sysName :: configure snmp sysName \"EXOS-Switch\"";
          type string;
          // NCS drop default statement
        }
      }
      container snmpv3 {
        leaf engine-id {
          type string;
        }
        container add {
          list access {
            // NCS patched for predictable order
            ordered-by user;
            tailf:cli-suppress-mode;
            key "group_name sec-model sec-level";
            leaf group_name {
              type string;
            }
            leaf sec-model {
              type string;
            }
            leaf sec-level {
              type string;
            }
            leaf read-view {
              type string;
            }
            leaf write-view {
              type string;
            }
            leaf notify-view {
              type string;
            }
          }
          list community {
            // NCS patched for predictable order
            ordered-by user;
            tailf:cli-suppress-mode;
            key "community_index";
            leaf community_index {
              type string;
            }
            leaf name {
              type string;
            }
            uses ncs_template_user-grouping;
          }
          list group {
            // NCS patched for predictable order
            ordered-by user;
            tailf:cli-suppress-mode;
            key "group_name user sec-model";
            leaf group_name {
              type string;
            }
            leaf user {
              type string;
            }
            leaf sec-model {
              type string;
            }
          }
          list target-addr {
            // NCS patched for predictable order
            ordered-by user;
            tailf:cli-suppress-mode;
            key "addr_name";
            leaf addr_name {
              type string;
            }
            leaf param {
              type string;
            }
            leaf ipaddress {
              type string;
            }
            leaf transport-port {
              type string;
            }
            leaf from {
              // NCS drop tailf-common:cli-diff-set-after statement
              // NCS drop tailf-common:cli-diff-delete-before statement
              type string;
            }
            leaf-list tag-list {
              // NCS patched for predictable order
              ordered-by user;
              tailf:cli-range-list-syntax;
              type string;
            }
          }
          list target-params {
            // NCS patched for predictable order
            ordered-by user;
            tailf:cli-suppress-mode;
            key "group_name";
            leaf group_name {
              type string;
            }
            uses ncs_template_user-grouping;
            leaf mp-model {
              type string;
            }
            leaf sec-model {
              type string;
            }
            leaf sec-level {
              type string;
            }
          }
          list user {
            // NCS patched for predictable order
            ordered-by user;
            extreme-xos:replace-input "(\\s+engine-id [0-9a-f:]+) :: ";
            tailf:cli-suppress-mode;
            key "user_name";
            leaf user_name {
              type string;
            }
            leaf authentication {
              type string;
            }
            container auth-encrypted {
              leaf localized-key {
                cli:secret " auth-encrypted localized-key (\\S+)" {
                  cli:arguments "always-encrypted";
                }
                extreme-xos:send-secret;
                type string;
              }
            }
            leaf privacy {
              type string;
            }
            leaf aes-bits {
              tailf:cli-drop-node-name;
              // NCS drop when statement
              type string;
            }
            leaf privacy-encrypted {
              type empty;
            }
            leaf localized-key {
              cli:secret " privacy-encrypted localized-key (\\S+)" {
                cli:arguments "always-encrypted";
              }
              extreme-xos:send-secret;
              type string;
            }
          }
        }
      }
      list vlan {
        // NCS patched for predictable order
        ordered-by user;
        tailf:cli-suppress-mode;
        key "id";
        leaf id {
          type string;
        }
        container delete {
          // NCS drop when statement
          list ports {
            // NCS patched for predictable order
            ordered-by user;
            // NCS drop tailf-common:cli-diff-set-after statement
            // NCS drop tailf-common:cli-diff-delete-before statement
            tailf:cli-suppress-mode;
            tailf:cli-range-list-syntax;
            key "id";
            leaf id {
              type string;
            }
          }
        }
        container add {
          list ports {
            // NCS patched for predictable order
            ordered-by user;
            // NCS drop tailf-common:cli-diff-set-after statement
            // NCS drop tailf-common:cli-diff-delete-before statement
            // NCS drop tailf-common:cli-diff-create-before statement
            // NCS drop tailf-common:cli-diff-create-after statement
            // NCS drop tailf-common:cli-diff-create-after statement
            tailf:cli-suppress-mode;
            tailf:cli-range-list-syntax;
            key "id";
            leaf id {
              type string;
            }
            choice tag {
              leaf untagged {
                type empty;
              }
              leaf tagged {
                type empty;
              }
            }
          }
        }
        container ipaddress {
          leaf ipaddress {
            // NCS drop tailf-common:cli-diff-set-after statement
            // NCS drop tailf-common:cli-diff-delete-before statement
            // NCS drop tailf-common:cli-diff-set-before statement
            tailf:cli-drop-node-name;
            type string;
          }
          leaf netmask {
            tailf:cli-drop-node-name;
            type string;
          }
        }
        leaf tag {
          // NCS drop tailf-common:cli-diff-set-after statement
          // NCS drop tailf-common:cli-diff-delete-before statement
          type string;
        }
        leaf description {
          // NCS drop tailf-common:cli-diff-set-after statement
          // NCS drop tailf-common:cli-diff-delete-before statement
          type string;
          // NCS drop default statement
        }
      }
      list vr {
        // NCS patched for predictable order
        ordered-by user;
        tailf:cli-suppress-mode;
        key "id";
        leaf id {
          type string;
        }
        container delete {
          // NCS drop when statement
          uses ncs_template_portList-grouping;
        }
        container add {
          leaf-list ports {
            // NCS patched for predictable order
            ordered-by user;
            // NCS drop tailf-common:cli-diff-create-after statement
            // NCS drop tailf-common:cli-diff-delete-before statement
            tailf:cli-range-list-syntax;
            type string;
          }
        }
      }
      container iproute {
        container add {
          container default {
            leaf gateway {
              tailf:cli-drop-node-name;
              type string;
            }
          }
          list route {
            // NCS patched for predictable order
            ordered-by user;
            tailf:cli-drop-node-name;
            tailf:cli-suppress-mode;
            key "address netmask gateway";
            leaf address {
              type string;
            }
            leaf netmask {
              type string;
            }
            leaf gateway {
              type string;
            }
          }
        }
      }
      container tacacs {
        extreme-xos:replace-delete-output "unconfigure tacacs (\\w+) server :: unconfigure tacacs server $1";
        extreme-xos:trim-delete-if-match "unconfigure.*shared-secret";
        uses ncs_template_tacacs-grouping;
        leaf priv-lvl {
          extreme-xos:replace-delete-output "unconfigure tacacs priv-lvl :: configure tacacs priv-lvl optional";
          // NCS drop tailf-common:ned-default-handling statement
          type string;
          // NCS drop default statement
        }
      }
      container tacacs-accounting {
        extreme-xos:replace-delete-output "unconfigure tacacs-accounting (\\w+) server :: unconfigure tacacs-accounting server $1";
        extreme-xos:trim-delete-if-match "unconfigure.*shared-secret";
        uses ncs_template_tacacs-grouping;
      }
      container banner {
        container before-login {
          leaf save-to-configuration {
            extreme-xos:replace-delete-output "unconfigure banner before-login save-to-configuration :: configure banner before-login save-to-configuration  ";
            extreme-xos:multi-line-banner;
            type string;
          }
        }
        leaf after-login {
          extreme-xos:replace-delete-output "unconfigure banner after-login :: configure banner after-login  ";
          extreme-xos:multi-line-banner;
          type string;
        }
      }
      container syslog {
        list add {
          // NCS patched for predictable order
          ordered-by user;
          // NCS drop tailf-common:cli-diff-create-after statement
          // NCS drop tailf-common:cli-diff-delete-before statement
          tailf:cli-suppress-mode;
          key "ipPort vr local";
          leaf ipPort {
            type string;
          }
          leaf vr {
            type string;
          }
          leaf local {
            tailf:cli-drop-node-name;
            type string;
          }
        }
      }
      container log {
        container target {
          list syslog {
            // NCS patched for predictable order
            ordered-by user;
            extreme-xos:replace-delete-output "unconfigure log target syslog :: configure syslog delete :: format,filter,match,from";
            extreme-xos:trim-delete-if-match "unconfigure log target syslog.*filter.*";
            extreme-xos:trim-delete-if-match "unconfigure log target syslog.*match.*";
            extreme-xos:trim-delete-if-match "unconfigure log target syslog.*from.*";
            // NCS drop tailf-common:cli-diff-create-after statement
            // NCS drop tailf-common:cli-diff-delete-before statement
            // NCS drop tailf-common:cli-diff-create-after statement
            // NCS drop tailf-common:cli-diff-delete-before statement
            tailf:cli-suppress-mode;
            key "ipPort vr local";
            leaf ipPort {
              type string;
            }
            leaf vr {
              type string;
            }
            leaf local {
              type string;
            }
            leaf from {
              // NCS drop tailf-common:cli-diff-set-after statement
              // NCS drop tailf-common:cli-diff-delete-before statement
              type string;
            }
            container filter {
              leaf filter {
                // NCS drop tailf-common:cli-diff-set-after statement
                // NCS drop tailf-common:cli-diff-delete-before statement
                tailf:cli-drop-node-name;
                type string;
              }
              leaf severity {
                type string;
              }
            }
            container format {
              leaf timestamp {
                // NCS drop tailf-common:cli-diff-set-after statement
                // NCS drop tailf-common:cli-diff-delete-before statement
                type string;
              }
              leaf date {
                type string;
              }
              leaf event-name {
                type string;
              }
              leaf priority {
                type empty;
              }
              leaf host-name {
                type empty;
              }
              leaf severity {
                type empty;
              }
              leaf tag-name {
                type empty;
              }
            }
            container match {
              choice regex-choice {
                leaf any {
                  // NCS drop tailf-common:cli-diff-set-after statement
                  // NCS drop tailf-common:cli-diff-delete-before statement
                  type empty;
                }
                leaf regex {
                  // NCS drop tailf-common:cli-diff-set-after statement
                  // NCS drop tailf-common:cli-diff-delete-before statement
                  tailf:cli-drop-node-name;
                  type string;
                }
              }
            }
          }
          list upm {
            // NCS patched for predictable order
            ordered-by user;
            // NCS drop tailf-common:cli-diff-delete-before statement
            // NCS drop tailf-common:cli-diff-create-after statement
            // NCS drop tailf-common:cli-diff-delete-before statement
            // NCS drop tailf-common:cli-diff-create-after statement
            // NCS drop tailf-common:cli-diff-delete-before statement
            // NCS drop tailf-common:cli-diff-delete-before statement
            tailf:cli-suppress-mode;
            key "name";
            leaf name {
              type string;
            }
            leaf filter {
              // NCS drop tailf-common:cli-diff-delete-before statement
              type string;
            }
            leaf severity {
              type string;
            }
          }
        }
        list filter {
          // NCS patched for predictable order
          ordered-by user;
          // NCS drop tailf-common:cli-diff-delete-before statement
          tailf:cli-suppress-mode;
          key "name";
          leaf name {
            type string;
          }
          container add {
            leaf-list events {
              // NCS patched for predictable order
              ordered-by user;
              extreme-xos:replace-delete-output "un(.*) add (.*) :: $1 delete $2";
              type string;
            }
          }
        }
      }
      container ports {
        list port_list {
          // NCS patched for predictable order
          ordered-by user;
          tailf:cli-drop-node-name;
          tailf:cli-suppress-mode;
          key "port";
          leaf port {
            type string;
          }
          container debounce {
            leaf time {
              type string;
              // NCS drop default statement
            }
          }
          leaf description-string {
            type string;
          }
          container rate-limit {
            container flood {
              leaf broadcast {
                extreme-xos:replace-delete-output "unconfigure (.*broadcast) \\d+ :: configure $1 no-limit";
                type string;
                // NCS drop default statement
              }
            }
          }
        }
      }
      container dns-client {
        container add {
          list name-server {
            // NCS patched for predictable order
            ordered-by user;
            // NCS drop tailf-common:cli-diff-create-after statement
            // NCS drop tailf-common:cli-diff-delete-before statement
            tailf:cli-suppress-mode;
            key "ip_address vr";
            leaf ip_address {
              type string;
            }
            leaf vr {
              type string;
            }
          }
          list domain-suffix {
            // NCS patched for predictable order
            ordered-by user;
            tailf:cli-suppress-mode;
            key "domain_name";
            leaf domain_name {
              type string;
            }
          }
        }
      }
      container sntp-client {
        container primary {
          uses ncs_template_sntpc-grouping;
        }
        container secondary {
          uses ncs_template_sntpc-grouping;
        }
      }
      container cli {
        extreme-xos:replace-delete-output "unconfigure cli max-sessions.* :: configure cli max-sessions 8";
        leaf max-sessions {
          type string;
          // NCS drop tailf-common:ned-default-handling statement
          // NCS drop default statement
        }
      }
      container timezone {
        leaf name {
          type string;
        }
        leaf gmt_offset {
          tailf:cli-drop-node-name;
          type string;
        }
        leaf autodst {
          tailf:cli-drop-node-name;
          type string;
          // NCS drop default statement
        }
      }
      container radius {
        list server {
          // NCS patched for predictable order
          ordered-by user;
          extreme-xos:replace-delete-output "(unconfigure radius) (\\d+) :: $1 server $2";
          tailf:cli-suppress-mode;
          tailf:cli-drop-node-name;
          key "index";
          leaf index {
            type string;
          }
          // NCS expand uses statement
          container shared-secret {
            leaf encrypted {
              cli:secret "encrypted <SECRET>" {
                cli:arguments "always-encrypted";
              }
              extreme-xos:send-secret;
              extreme-xos:quoted-string;
              type string;
            }
          }
        }
        container netlogin {
          list server {
            // NCS patched for predictable order
            ordered-by user;
            extreme-xos:replace-delete-output "(unconfigure radius) netlogin (\\d+) :: $1 server $2";
            tailf:cli-drop-node-name;
            tailf:cli-suppress-mode;
            key "index";
            leaf index {
              type string;
            }
            leaf server {
              type string;
            }
            leaf udp-port {
              tailf:cli-drop-node-name;
              type string;
            }
            leaf client-ip {
              type string;
            }
            // NCS expand uses statement
            leaf vr {
              // NCS drop tailf-common:cli-diff-create-after statement
              // NCS drop tailf-common:cli-diff-delete-before statement
              type string;
            }
          }
          uses ncs_template_radius-timeout-grouping;
        }
        list dynamic-authorization {
          // NCS patched for predictable order
          ordered-by user;
          extreme-xos:replace-delete-output "(unconfigure.*) (\\d+) :: $1 server $2";
          tailf:cli-suppress-mode;
          key "index";
          leaf index {
            type string;
          }
          container server {
            leaf host {
              tailf:cli-drop-node-name;
              type string;
            }
            leaf client-ip {
              type string;
            }
            // NCS expand uses statement
            leaf vr {
              // NCS drop tailf-common:cli-diff-create-after statement
              // NCS drop tailf-common:cli-diff-delete-before statement
              type string;
            }
            // NCS expand uses statement
            container shared-secret {
              leaf encrypted {
                cli:secret "encrypted <SECRET>" {
                  cli:arguments "always-encrypted";
                }
                extreme-xos:send-secret;
                extreme-xos:quoted-string;
                type string;
              }
            }
          }
          leaf nas-ip {
            type string;
            // NCS drop default statement
          }
        }
        container mgmt-access {
          uses ncs_template_radius-timeout-grouping;
        }
        uses ncs_template_radius-timeout-grouping;
      }
      container netlogin {
        // NCS drop tailf-common:cli-diff-dependency statement
        container add {
          list mac-list {
            // NCS patched for predictable order
            ordered-by user;
            tailf:cli-suppress-mode;
            key "mac mask";
            leaf mac {
              type string;
            }
            leaf mask {
              type string;
            }
            leaf ports {
              type string;
            }
          }
        }
        container mac {
          container authentication {
            container database-order {
              leaf local {
                type empty;
              }
              leaf radius {
                type empty;
              }
            }
          }
          list ports {
            // NCS patched for predictable order
            ordered-by user;
            tailf:cli-suppress-mode;
            tailf:cli-range-list-syntax;
            key "id";
            leaf id {
              type string;
            }
            container timers {
              leaf delay {
                extreme-xos:replace-delete-output "un(.*) :: $1 0";
                type string;
                // NCS drop default statement
              }
              container reauth-wrap {
                tailf:cli-drop-node-name;
                extreme-xos:replace-delete-output "un(.* reauth-period).*(reauthentication).* :: $1 3600 $2 off";
                leaf reauth-period {
                  type string;
                  // NCS drop default statement
                }
                leaf reauthentication {
                  type string;
                  // NCS drop default statement
                }
              }
            }
          }
        }
        container dot1x {
          list ports {
            // NCS patched for predictable order
            ordered-by user;
            tailf:cli-suppress-mode;
            tailf:cli-range-list-syntax;
            key "id";
            leaf id {
              type string;
            }
            container timers {
              extreme-xos:replace-delete-output "un(.* server-timeout).*(quiet-period).*(supp-resp-timeout).* :: $1 30 $2 60 $3 30";
              leaf server-timeout {
                type string;
                // NCS drop default statement
              }
              leaf quiet-period {
                type string;
                // NCS drop default statement
              }
              leaf supp-resp-timeout {
                type string;
                // NCS drop default statement
              }
            }
          }
        }
        list ports {
          // NCS patched for predictable order
          ordered-by user;
          extreme-xos:trim-delete-if-match "unconfigure netlogin ports \\S+";
          tailf:cli-suppress-mode;
          tailf:cli-range-list-syntax;
          key "id";
          leaf id {
            type string;
          }
          leaf mode {
            type string;
          }
        }
        container authentication {
          leaf protocol-order {
            // NCS drop tailf-common:cli-diff-set-after statement
            extreme-xos:replace-delete-output "un(.*) :: $1 dot1x web-based mac cep";
            type string;
          }
        }
        leaf vlan {
          // NCS drop tailf-common:cli-diff-set-after statement
          // NCS drop tailf-common:cli-diff-delete-before statement
          type string;
        }
      }
      container policy {
        leaf rule-model {
          // NCS drop tailf-common:cli-diff-delete-after statement
          // NCS drop tailf-common:cli-diff-set-before statement
          extreme-xos:replace-delete-output "un(.*) :: $1 hierarchical";
          type string;
          // NCS drop default statement
        }
        container slices {
          leaf tci-overwrite {
            // NCS drop tailf-common:cli-diff-set-before statement
            extreme-xos:replace-delete-output "un(.*) :: $1 4";
            type string;
            // NCS drop default statement
          }
          leaf shared {
            // NCS drop tailf-common:cli-diff-delete-before statement
            // NCS drop tailf-common:cli-diff-set-before statement
            extreme-xos:replace-delete-output "un(.*) :: $1 0";
            type string;
            // NCS drop default statement
          }
        }
        container maptable {
          leaf response {
            type string;
          }
        }
        container vlanauthorization {
          leaf enable {
            extreme-xos:replace-delete-output "un(.*) :: $1 disable";
            type empty;
          }
        }
        list profile {
          // NCS patched for predictable order
          ordered-by user;
          tailf:cli-suppress-mode;
          key "index";
          leaf index {
            type string;
          }
          leaf name {
            type string;
          }
          leaf access-list {
            type string;
          }
          leaf pvid-status {
            type string;
          }
          leaf pvid {
            type string;
          }
          leaf web-redirect {
            type string;
          }
        }
        container captive-portal {
          leaf-list listening {
            // NCS patched for predictable order
            ordered-by user;
            type string;
          }
          list web-redirect {
            // NCS patched for predictable order
            ordered-by user;
            tailf:cli-suppress-mode;
            key "index server";
            leaf index {
              type string;
            }
            leaf server {
              type string;
            }
            leaf url {
              type string;
            }
            leaf status {
              tailf:cli-drop-node-name;
              type string;
            }
          }
        }
      }
      list stpd {
        // NCS patched for predictable order
        ordered-by user;
        tailf:cli-suppress-mode;
        // NCS drop tailf-common:cli-diff-create-after statement
        // NCS drop tailf-common:cli-diff-delete-before statement
        extreme-xos:trim-delete-if-match "unconfigure.*mode dot1d.*";
        key "name";
        leaf name {
          type string;
        }
        container ports {
          container edge-safeguard {
            uses ncs_template_ports-enable-grouping;
          }
          container bpdu-restrict {
            uses ncs_template_ports-enable-grouping;
          }
          list link-type {
            // NCS patched for predictable order
            ordered-by user;
            tailf:cli-suppress-mode;
            tailf:cli-range-list-syntax;
            // NCS drop tailf-common:cli-diff-create-after statement
            // NCS drop tailf-common:cli-diff-delete-before statement
            // NCS drop tailf-common:cli-diff-create-after statement
            // NCS drop tailf-common:cli-diff-delete-before statement
            key "ports";
            leaf ports {
              type string;
            }
            leaf edge {
              type empty;
            }
          }
        }
        list add {
          // NCS patched for predictable order
          ordered-by user;
          tailf:cli-suppress-mode;
          key "vlan";
          leaf vlan {
            type string;
          }
          leaf-list ports {
            // NCS patched for predictable order
            ordered-by user;
            // NCS drop tailf-common:cli-diff-set-after statement
            // NCS drop tailf-common:cli-diff-delete-before statement
            tailf:cli-range-list-syntax;
            type string;
          }
          leaf dot1d {
            type empty;
          }
        }
      }
      container cdp {
        list voip-vlan {
          // NCS patched for predictable order
          ordered-by user;
          extreme-xos:replace-delete-output "un(configure cdp voip-vlan) \\S+ (.*) :: $1 none $2";
          tailf:cli-suppress-mode;
          // NCS drop tailf-common:cli-diff-set-after statement
          // NCS drop tailf-common:cli-diff-delete-before statement
          key "vlan_name";
          leaf vlan_name {
            type string;
          }
          uses ncs_template_port-list-grouping;
        }
      }
      container lldp {
        list ports {
          // NCS patched for predictable order
          ordered-by user;
          // NCS drop tailf-common:cli-diff-set-after statement
          // NCS drop tailf-common:cli-diff-delete-before statement
          tailf:cli-suppress-mode;
          tailf:cli-range-list-syntax;
          key "id";
          leaf id {
            type string;
          }
          container advertise {
            leaf port-description {
              type empty;
            }
            leaf system-capabilities {
              type empty;
            }
            leaf management-address {
              type empty;
            }
          }
        }
      }
      container inline-power {
        container detection {
          list portlist {
            // NCS patched for predictable order
            ordered-by user;
            tailf:cli-drop-node-name;
            // NCS drop tailf-common:cli-diff-set-after statement
            // NCS drop tailf-common:cli-diff-delete-before statement
            tailf:cli-suppress-mode;
            tailf:cli-range-list-syntax;
            key "ports";
            leaf ports {
              type string;
            }
            leaf "legacy-and-802.3af" {
              type string;
            }
          }
        }
      }
    }
    container enable {
      extreme-xos:no-to-disable;
      container snmp {
        container access {
          presence "true";
          leaf snmp-v1v2c {
            type empty;
          }
          leaf snmpv3 {
            type empty;
          }
        }
        container traps {
          leaf fdb {
            type string;
          }
          container configuration {
            leaf change {
              type empty;
            }
            leaf save {
              type empty;
            }
          }
        }
      }
      leaf ssh2 {
        type empty;
      }
      leaf cli-config-logging {
        type empty;
      }
      leaf tacacs {
        type empty;
      }
      leaf tacacs-accounting {
        type empty;
      }
      leaf tacacs-authorization {
        type empty;
      }
      leaf sntp-client {
        type empty;
      }
      container log {
        leaf debug-mode {
          type empty;
        }
        container target {
          list syslog {
            // NCS patched for predictable order
            ordered-by user;
            // NCS drop tailf-common:cli-diff-create-after statement
            // NCS drop tailf-common:cli-diff-delete-before statement
            tailf:cli-suppress-mode;
            key "ipPort vr local";
            leaf ipPort {
              type string;
            }
            leaf vr {
              type string;
            }
            leaf local {
              tailf:cli-drop-node-name;
              type string;
            }
          }
          leaf-list upm {
            // NCS patched for predictable order
            ordered-by user;
            // NCS drop tailf-common:cli-diff-create-after statement
            // NCS drop tailf-common:cli-diff-delete-before statement
            // NCS drop tailf-common:cli-diff-modify-before statement
            type string;
          }
        }
      }
      container cli {
        leaf config-logging {
          type empty;
        }
      }
      container loopback-mode {
        list vlan {
          // NCS patched for predictable order
          ordered-by user;
          // NCS drop tailf-common:cli-diff-set-after statement
          // NCS drop tailf-common:cli-diff-delete-before statement
          tailf:cli-suppress-mode;
          key "id";
          leaf id {
            type string;
          }
        }
      }
      container ipforwarding {
        list vlan {
          // NCS patched for predictable order
          ordered-by user;
          tailf:cli-suppress-mode;
          // NCS drop tailf-common:cli-diff-set-after statement
          // NCS drop tailf-common:cli-diff-delete-before statement
          // NCS drop tailf-common:cli-diff-set-after statement
          // NCS drop tailf-common:cli-diff-delete-before statement
          key "id";
          leaf id {
            type string;
          }
        }
      }
      container diffserv {
        uses ncs_template_exam-grouping;
      }
      container radius {
        leaf netlogin {
          type empty;
        }
        leaf dynamic-authorization {
          type empty;
        }
      }
      list stpd {
        // NCS patched for predictable order
        ordered-by user;
        tailf:cli-suppress-mode;
        // NCS drop tailf-common:cli-diff-set-after statement
        // NCS drop tailf-common:cli-diff-delete-before statement
        key "name";
        leaf name {
          type string;
        }
        container auto-bind {
          // NCS expand uses statement
          leaf-list vlan {
            // NCS patched for predictable order
            ordered-by user;
            // NCS drop tailf-common:cli-diff-set-after statement
            // NCS drop tailf-common:cli-diff-delete-before statement
            type string;
            // NCS drop tailf-common:cli-diff-delete-after statement
          }
        }
      }
      container netlogin {
        list ports {
          // NCS patched for predictable order
          ordered-by user;
          // NCS drop tailf-common:cli-diff-set-after statement
          // NCS drop tailf-common:cli-diff-delete-before statement
          tailf:cli-suppress-mode;
          tailf:cli-range-list-syntax;
          key "id";
          leaf id {
            type string;
          }
          uses ncs_template_netlogin-authprotocol-grouping;
        }
        container dot1x-max {
          tailf:cli-drop-node-name;
          // NCS expand uses statement
          leaf dot1x {
            type empty;
            // NCS drop tailf-common:cli-diff-set-after statement
            // NCS drop tailf-common:cli-diff-delete-before statement
          }
          leaf mac {
            type empty;
            // NCS drop tailf-common:cli-diff-set-after statement
            // NCS drop tailf-common:cli-diff-delete-before statement
          }
          leaf web-based {
            type empty;
            // NCS drop tailf-common:cli-diff-set-after statement
            // NCS drop tailf-common:cli-diff-delete-before statement
          }
        }
      }
      leaf policy {
        type empty;
      }
      container cdp {
        uses ncs_template_port-list-grouping;
      }
      container ip-security {
        container dhcp-snooping {
          list vlan {
            // NCS patched for predictable order
            ordered-by user;
            // NCS drop tailf-common:cli-diff-set-after statement
            // NCS drop tailf-common:cli-diff-delete-before statement
            // NCS drop tailf-common:cli-diff-set-after statement
            // NCS drop tailf-common:cli-diff-delete-before statement
            tailf:cli-suppress-mode;
            key "id";
            leaf id {
              type string;
            }
            list ports {
              // NCS patched for predictable order
              ordered-by user;
              // NCS drop tailf-common:cli-diff-set-after statement
              // NCS drop tailf-common:cli-diff-delete-before statement
              // NCS drop tailf-common:cli-diff-set-after statement
              // NCS drop tailf-common:cli-diff-delete-before statement
              // NCS drop tailf-common:cli-diff-delete-before statement
              tailf:cli-suppress-mode;
              tailf:cli-range-list-syntax;
              key "id";
              leaf id {
                type string;
              }
              leaf violation-action {
                type string;
              }
            }
          }
        }
      }
    }
    container disable {
      extreme-xos:no-to-disable;
      leaf telnet {
        type empty;
      }
      list stpd {
        // NCS patched for predictable order
        ordered-by user;
        tailf:cli-suppress-mode;
        key "stpd_name";
        leaf stpd_name {
          type string;
        }
      }
      container snmp {
        container traps {
          container port-up-down {
            leaf-list port {
              // NCS patched for predictable order
              ordered-by user;
              tailf:cli-range-list-syntax;
              type string;
            }
          }
        }
      }
      container dot1p {
        uses ncs_template_exam-grouping;
      }
      container edp {
        uses ncs_template_port-list-grouping;
      }
    }
  }
  augment "/ncs:compliance/ncs:template/ncs:ned-id/ncs:config" {
    container create {
      extreme-xos:delete-with "delete";
      list account {
        // NCS patched for predictable order
        ordered-by user;
        tailf:cli-suppress-mode;
        key "account-name";
        leaf account-name {
          type string;
        }
        leaf account-type {
          tailf:cli-drop-node-name;
          type string;
        }
        leaf encrypted {
          cli:secret "encrypted <SECRET>" {
            cli:arguments "always-encrypted";
          }
          extreme-xos:accounts-password;
          type string;
        }
        leaf old-password {
          type string;
          tailf:cli-drop-node-name;
        }
      }
      list access-list {
        // NCS patched for predictable order
        ordered-by user;
        extreme-xos:redeploy-access-profile-at-acl-modify;
        tailf:cli-suppress-mode;
        key "dynamic-rule";
        leaf dynamic-rule {
          type string;
        }
        leaf conditions {
          tailf:cli-drop-node-name;
          type string;
        }
        leaf actions {
          tailf:cli-drop-node-name;
          type string;
        }
        leaf application {
          type string;
        }
      }
      list vlan {
        // NCS patched for predictable order
        ordered-by user;
        // NCS drop tailf-common:cli-diff-create-after statement
        // NCS drop tailf-common:cli-diff-delete-before statement
        tailf:cli-suppress-mode;
        key "id";
        leaf id {
          type string;
        }
        leaf vr {
          type string;
        }
      }
      list vr {
        // NCS patched for predictable order
        ordered-by user;
        tailf:cli-suppress-mode;
        key "id";
        leaf id {
          type string;
        }
      }
      leaf-list qosprofile {
        // NCS patched for predictable order
        ordered-by user;
        type string;
      }
      container log {
        leaf-list filter {
          // NCS patched for predictable order
          ordered-by user;
          type string;
        }
        container target {
          leaf-list upm {
            // NCS patched for predictable order
            ordered-by user;
            // NCS drop tailf-common:cli-diff-delete-before statement
            // NCS drop tailf-common:cli-diff-modify-before statement
            // NCS drop tailf-common:cli-diff-delete-before statement
            // NCS drop tailf-common:cli-diff-create-after statement
            // NCS drop tailf-common:cli-diff-delete-before statement
            // NCS drop tailf-common:cli-diff-create-after statement
            type string;
          }
        }
      }
      container upm {
        list profile {
          // NCS patched for predictable order
          ordered-by user;
          extreme-xos:remove-before-change;
          key "name";
          leaf name {
            type string;
          }
          leaf commands {
            tailf:cli-drop-node-name;
            extreme-xos:upm-list-out;
            type string;
          }
        }
      }
      list stpd {
        // NCS patched for predictable order
        ordered-by user;
        tailf:cli-suppress-mode;
        key "name";
        leaf name {
          type string;
        }
      }
    }
    container configure {
      extreme-xos:delete-with "unconfigure";
      extreme-xos:trim-delete-if-match "unconfigure vlan \\S* tag";
      extreme-xos:trim-delete-if-match "unconfigure timezone.*";
      extreme-xos:trim-delete-if-match "unconfigure account.*";
      extreme-xos:trim-delete-if-match "unconfigure log target upm.*";
      list access-list {
        // NCS patched for predictable order
        ordered-by user;
        // NCS drop tailf-common:cli-diff-create-after statement
        // NCS drop tailf-common:cli-diff-delete-before statement
        tailf:cli-suppress-mode;
        key "aclname";
        leaf aclname {
          type string;
        }
        leaf any {
          type string;
        }
      }
      container snmp {
        container access-profile {
          list add {
            // NCS patched for predictable order
            ordered-by user;
            // NCS drop tailf-common:cli-diff-create-after statement
            // NCS drop tailf-common:cli-diff-delete-before statement
            tailf:cli-suppress-mode;
            key "rule";
            leaf rule {
              type string;
            }
            leaf condition {
              tailf:cli-drop-node-name;
              type string;
            }
            leaf previous_rule {
              tailf:cli-drop-node-name;
              type string;
            }
          }
        }
        leaf sysContact {
          extreme-xos:replace-delete-output "unconfigure snmp sysContact :: configure snmp sysContact \"support@extremenetworks.com, +1 888 257 3000\"";
          type string;
          // NCS drop default statement
        }
        leaf sysLocation {
          extreme-xos:replace-delete-output "unconfigure snmp sysLocation :: configure snmp sysLocation \"NO LOCATION PROVIDED\"";
          type string;
          // NCS drop default statement
        }
        leaf sysName {
          extreme-xos:replace-delete-output "unconfigure snmp sysName :: configure snmp sysName \"EXOS-Switch\"";
          type string;
          // NCS drop default statement
        }
      }
      container snmpv3 {
        leaf engine-id {
          type string;
        }
        container add {
          list access {
            // NCS patched for predictable order
            ordered-by user;
            tailf:cli-suppress-mode;
            key "group_name sec-model sec-level";
            leaf group_name {
              type string;
            }
            leaf sec-model {
              type string;
            }
            leaf sec-level {
              type string;
            }
            leaf read-view {
              type string;
            }
            leaf write-view {
              type string;
            }
            leaf notify-view {
              type string;
            }
          }
          list community {
            // NCS patched for predictable order
            ordered-by user;
            tailf:cli-suppress-mode;
            key "community_index";
            leaf community_index {
              type string;
            }
            leaf name {
              type string;
            }
            uses ncs_compliance_template_user-grouping;
          }
          list group {
            // NCS patched for predictable order
            ordered-by user;
            tailf:cli-suppress-mode;
            key "group_name user sec-model";
            leaf group_name {
              type string;
            }
            leaf user {
              type string;
            }
            leaf sec-model {
              type string;
            }
          }
          list target-addr {
            // NCS patched for predictable order
            ordered-by user;
            tailf:cli-suppress-mode;
            key "addr_name";
            leaf addr_name {
              type string;
            }
            leaf param {
              type string;
            }
            leaf ipaddress {
              type string;
            }
            leaf transport-port {
              type string;
            }
            leaf from {
              // NCS drop tailf-common:cli-diff-set-after statement
              // NCS drop tailf-common:cli-diff-delete-before statement
              type string;
            }
            leaf-list tag-list {
              // NCS patched for predictable order
              ordered-by user;
              tailf:cli-range-list-syntax;
              type string;
            }
          }
          list target-params {
            // NCS patched for predictable order
            ordered-by user;
            tailf:cli-suppress-mode;
            key "group_name";
            leaf group_name {
              type string;
            }
            uses ncs_compliance_template_user-grouping;
            leaf mp-model {
              type string;
            }
            leaf sec-model {
              type string;
            }
            leaf sec-level {
              type string;
            }
          }
          list user {
            // NCS patched for predictable order
            ordered-by user;
            extreme-xos:replace-input "(\\s+engine-id [0-9a-f:]+) :: ";
            tailf:cli-suppress-mode;
            key "user_name";
            leaf user_name {
              type string;
            }
            leaf authentication {
              type string;
            }
            container auth-encrypted {
              leaf localized-key {
                cli:secret " auth-encrypted localized-key (\\S+)" {
                  cli:arguments "always-encrypted";
                }
                extreme-xos:send-secret;
                type string;
              }
            }
            leaf privacy {
              type string;
            }
            leaf aes-bits {
              tailf:cli-drop-node-name;
              // NCS drop when statement
              type string;
            }
            leaf privacy-encrypted {
              type empty;
            }
            leaf localized-key {
              cli:secret " privacy-encrypted localized-key (\\S+)" {
                cli:arguments "always-encrypted";
              }
              extreme-xos:send-secret;
              type string;
            }
          }
        }
      }
      list vlan {
        // NCS patched for predictable order
        ordered-by user;
        tailf:cli-suppress-mode;
        key "id";
        leaf id {
          type string;
        }
        container delete {
          // NCS drop when statement
          list ports {
            // NCS patched for predictable order
            ordered-by user;
            // NCS drop tailf-common:cli-diff-set-after statement
            // NCS drop tailf-common:cli-diff-delete-before statement
            tailf:cli-suppress-mode;
            tailf:cli-range-list-syntax;
            key "id";
            leaf id {
              type string;
            }
          }
        }
        container add {
          list ports {
            // NCS patched for predictable order
            ordered-by user;
            // NCS drop tailf-common:cli-diff-set-after statement
            // NCS drop tailf-common:cli-diff-delete-before statement
            // NCS drop tailf-common:cli-diff-create-before statement
            // NCS drop tailf-common:cli-diff-create-after statement
            // NCS drop tailf-common:cli-diff-create-after statement
            tailf:cli-suppress-mode;
            tailf:cli-range-list-syntax;
            key "id";
            leaf id {
              type string;
            }
            choice tag {
              leaf untagged {
                type empty;
              }
              leaf tagged {
                type empty;
              }
            }
          }
        }
        container ipaddress {
          leaf ipaddress {
            // NCS drop tailf-common:cli-diff-set-after statement
            // NCS drop tailf-common:cli-diff-delete-before statement
            // NCS drop tailf-common:cli-diff-set-before statement
            tailf:cli-drop-node-name;
            type string;
          }
          leaf netmask {
            tailf:cli-drop-node-name;
            type string;
          }
        }
        leaf tag {
          // NCS drop tailf-common:cli-diff-set-after statement
          // NCS drop tailf-common:cli-diff-delete-before statement
          type string;
        }
        leaf description {
          // NCS drop tailf-common:cli-diff-set-after statement
          // NCS drop tailf-common:cli-diff-delete-before statement
          type string;
          // NCS drop default statement
        }
      }
      list vr {
        // NCS patched for predictable order
        ordered-by user;
        tailf:cli-suppress-mode;
        key "id";
        leaf id {
          type string;
        }
        container delete {
          // NCS drop when statement
          uses ncs_compliance_template_portList-grouping;
        }
        container add {
          leaf-list ports {
            // NCS patched for predictable order
            ordered-by user;
            // NCS drop tailf-common:cli-diff-create-after statement
            // NCS drop tailf-common:cli-diff-delete-before statement
            tailf:cli-range-list-syntax;
            type string;
          }
        }
      }
      container iproute {
        container add {
          container default {
            leaf gateway {
              tailf:cli-drop-node-name;
              type string;
            }
          }
          list route {
            // NCS patched for predictable order
            ordered-by user;
            tailf:cli-drop-node-name;
            tailf:cli-suppress-mode;
            key "address netmask gateway";
            leaf address {
              type string;
            }
            leaf netmask {
              type string;
            }
            leaf gateway {
              type string;
            }
          }
        }
      }
      container tacacs {
        extreme-xos:replace-delete-output "unconfigure tacacs (\\w+) server :: unconfigure tacacs server $1";
        extreme-xos:trim-delete-if-match "unconfigure.*shared-secret";
        uses ncs_compliance_template_tacacs-grouping;
        leaf priv-lvl {
          extreme-xos:replace-delete-output "unconfigure tacacs priv-lvl :: configure tacacs priv-lvl optional";
          // NCS drop tailf-common:ned-default-handling statement
          type string;
          // NCS drop default statement
        }
      }
      container tacacs-accounting {
        extreme-xos:replace-delete-output "unconfigure tacacs-accounting (\\w+) server :: unconfigure tacacs-accounting server $1";
        extreme-xos:trim-delete-if-match "unconfigure.*shared-secret";
        uses ncs_compliance_template_tacacs-grouping;
      }
      container banner {
        container before-login {
          leaf save-to-configuration {
            extreme-xos:replace-delete-output "unconfigure banner before-login save-to-configuration :: configure banner before-login save-to-configuration  ";
            extreme-xos:multi-line-banner;
            type string;
          }
        }
        leaf after-login {
          extreme-xos:replace-delete-output "unconfigure banner after-login :: configure banner after-login  ";
          extreme-xos:multi-line-banner;
          type string;
        }
      }
      container syslog {
        list add {
          // NCS patched for predictable order
          ordered-by user;
          // NCS drop tailf-common:cli-diff-create-after statement
          // NCS drop tailf-common:cli-diff-delete-before statement
          tailf:cli-suppress-mode;
          key "ipPort vr local";
          leaf ipPort {
            type string;
          }
          leaf vr {
            type string;
          }
          leaf local {
            tailf:cli-drop-node-name;
            type string;
          }
        }
      }
      container log {
        container target {
          list syslog {
            // NCS patched for predictable order
            ordered-by user;
            extreme-xos:replace-delete-output "unconfigure log target syslog :: configure syslog delete :: format,filter,match,from";
            extreme-xos:trim-delete-if-match "unconfigure log target syslog.*filter.*";
            extreme-xos:trim-delete-if-match "unconfigure log target syslog.*match.*";
            extreme-xos:trim-delete-if-match "unconfigure log target syslog.*from.*";
            // NCS drop tailf-common:cli-diff-create-after statement
            // NCS drop tailf-common:cli-diff-delete-before statement
            // NCS drop tailf-common:cli-diff-create-after statement
            // NCS drop tailf-common:cli-diff-delete-before statement
            tailf:cli-suppress-mode;
            key "ipPort vr local";
            leaf ipPort {
              type string;
            }
            leaf vr {
              type string;
            }
            leaf local {
              type string;
            }
            leaf from {
              // NCS drop tailf-common:cli-diff-set-after statement
              // NCS drop tailf-common:cli-diff-delete-before statement
              type string;
            }
            container filter {
              leaf filter {
                // NCS drop tailf-common:cli-diff-set-after statement
                // NCS drop tailf-common:cli-diff-delete-before statement
                tailf:cli-drop-node-name;
                type string;
              }
              leaf severity {
                type string;
              }
            }
            container format {
              leaf timestamp {
                // NCS drop tailf-common:cli-diff-set-after statement
                // NCS drop tailf-common:cli-diff-delete-before statement
                type string;
              }
              leaf date {
                type string;
              }
              leaf event-name {
                type string;
              }
              leaf priority {
                type empty;
              }
              leaf host-name {
                type empty;
              }
              leaf severity {
                type empty;
              }
              leaf tag-name {
                type empty;
              }
            }
            container match {
              choice regex-choice {
                leaf any {
                  // NCS drop tailf-common:cli-diff-set-after statement
                  // NCS drop tailf-common:cli-diff-delete-before statement
                  type empty;
                }
                leaf regex {
                  // NCS drop tailf-common:cli-diff-set-after statement
                  // NCS drop tailf-common:cli-diff-delete-before statement
                  tailf:cli-drop-node-name;
                  type string;
                }
              }
            }
          }
          list upm {
            // NCS patched for predictable order
            ordered-by user;
            // NCS drop tailf-common:cli-diff-delete-before statement
            // NCS drop tailf-common:cli-diff-create-after statement
            // NCS drop tailf-common:cli-diff-delete-before statement
            // NCS drop tailf-common:cli-diff-create-after statement
            // NCS drop tailf-common:cli-diff-delete-before statement
            // NCS drop tailf-common:cli-diff-delete-before statement
            tailf:cli-suppress-mode;
            key "name";
            leaf name {
              type string;
            }
            leaf filter {
              // NCS drop tailf-common:cli-diff-delete-before statement
              type string;
            }
            leaf severity {
              type string;
            }
          }
        }
        list filter {
          // NCS patched for predictable order
          ordered-by user;
          // NCS drop tailf-common:cli-diff-delete-before statement
          tailf:cli-suppress-mode;
          key "name";
          leaf name {
            type string;
          }
          container add {
            leaf-list events {
              // NCS patched for predictable order
              ordered-by user;
              extreme-xos:replace-delete-output "un(.*) add (.*) :: $1 delete $2";
              type string;
            }
          }
        }
      }
      container ports {
        list port_list {
          // NCS patched for predictable order
          ordered-by user;
          tailf:cli-drop-node-name;
          tailf:cli-suppress-mode;
          key "port";
          leaf port {
            type string;
          }
          container debounce {
            leaf time {
              type string;
              // NCS drop default statement
            }
          }
          leaf description-string {
            type string;
          }
          container rate-limit {
            container flood {
              leaf broadcast {
                extreme-xos:replace-delete-output "unconfigure (.*broadcast) \\d+ :: configure $1 no-limit";
                type string;
                // NCS drop default statement
              }
            }
          }
        }
      }
      container dns-client {
        container add {
          list name-server {
            // NCS patched for predictable order
            ordered-by user;
            // NCS drop tailf-common:cli-diff-create-after statement
            // NCS drop tailf-common:cli-diff-delete-before statement
            tailf:cli-suppress-mode;
            key "ip_address vr";
            leaf ip_address {
              type string;
            }
            leaf vr {
              type string;
            }
          }
          list domain-suffix {
            // NCS patched for predictable order
            ordered-by user;
            tailf:cli-suppress-mode;
            key "domain_name";
            leaf domain_name {
              type string;
            }
          }
        }
      }
      container sntp-client {
        container primary {
          uses ncs_compliance_template_sntpc-grouping;
        }
        container secondary {
          uses ncs_compliance_template_sntpc-grouping;
        }
      }
      container cli {
        extreme-xos:replace-delete-output "unconfigure cli max-sessions.* :: configure cli max-sessions 8";
        leaf max-sessions {
          type string;
          // NCS drop tailf-common:ned-default-handling statement
          // NCS drop default statement
        }
      }
      container timezone {
        leaf name {
          type string;
        }
        leaf gmt_offset {
          tailf:cli-drop-node-name;
          type string;
        }
        leaf autodst {
          tailf:cli-drop-node-name;
          type string;
          // NCS drop default statement
        }
      }
      container radius {
        list server {
          // NCS patched for predictable order
          ordered-by user;
          extreme-xos:replace-delete-output "(unconfigure radius) (\\d+) :: $1 server $2";
          tailf:cli-suppress-mode;
          tailf:cli-drop-node-name;
          key "index";
          leaf index {
            type string;
          }
          // NCS expand uses statement
          container shared-secret {
            leaf encrypted {
              cli:secret "encrypted <SECRET>" {
                cli:arguments "always-encrypted";
              }
              extreme-xos:send-secret;
              extreme-xos:quoted-string;
              type string;
            }
          }
        }
        container netlogin {
          list server {
            // NCS patched for predictable order
            ordered-by user;
            extreme-xos:replace-delete-output "(unconfigure radius) netlogin (\\d+) :: $1 server $2";
            tailf:cli-drop-node-name;
            tailf:cli-suppress-mode;
            key "index";
            leaf index {
              type string;
            }
            leaf server {
              type string;
            }
            leaf udp-port {
              tailf:cli-drop-node-name;
              type string;
            }
            leaf client-ip {
              type string;
            }
            // NCS expand uses statement
            leaf vr {
              // NCS drop tailf-common:cli-diff-create-after statement
              // NCS drop tailf-common:cli-diff-delete-before statement
              type string;
            }
          }
          uses ncs_compliance_template_radius-timeout-grouping;
        }
        list dynamic-authorization {
          // NCS patched for predictable order
          ordered-by user;
          extreme-xos:replace-delete-output "(unconfigure.*) (\\d+) :: $1 server $2";
          tailf:cli-suppress-mode;
          key "index";
          leaf index {
            type string;
          }
          container server {
            leaf host {
              tailf:cli-drop-node-name;
              type string;
            }
            leaf client-ip {
              type string;
            }
            // NCS expand uses statement
            leaf vr {
              // NCS drop tailf-common:cli-diff-create-after statement
              // NCS drop tailf-common:cli-diff-delete-before statement
              type string;
            }
            // NCS expand uses statement
            container shared-secret {
              leaf encrypted {
                cli:secret "encrypted <SECRET>" {
                  cli:arguments "always-encrypted";
                }
                extreme-xos:send-secret;
                extreme-xos:quoted-string;
                type string;
              }
            }
          }
          leaf nas-ip {
            type string;
            // NCS drop default statement
          }
        }
        container mgmt-access {
          uses ncs_compliance_template_radius-timeout-grouping;
        }
        uses ncs_compliance_template_radius-timeout-grouping;
      }
      container netlogin {
        // NCS drop tailf-common:cli-diff-dependency statement
        container add {
          list mac-list {
            // NCS patched for predictable order
            ordered-by user;
            tailf:cli-suppress-mode;
            key "mac mask";
            leaf mac {
              type string;
            }
            leaf mask {
              type string;
            }
            leaf ports {
              type string;
            }
          }
        }
        container mac {
          container authentication {
            container database-order {
              leaf local {
                type empty;
              }
              leaf radius {
                type empty;
              }
            }
          }
          list ports {
            // NCS patched for predictable order
            ordered-by user;
            tailf:cli-suppress-mode;
            tailf:cli-range-list-syntax;
            key "id";
            leaf id {
              type string;
            }
            container timers {
              leaf delay {
                extreme-xos:replace-delete-output "un(.*) :: $1 0";
                type string;
                // NCS drop default statement
              }
              container reauth-wrap {
                tailf:cli-drop-node-name;
                extreme-xos:replace-delete-output "un(.* reauth-period).*(reauthentication).* :: $1 3600 $2 off";
                leaf reauth-period {
                  type string;
                  // NCS drop default statement
                }
                leaf reauthentication {
                  type string;
                  // NCS drop default statement
                }
              }
            }
          }
        }
        container dot1x {
          list ports {
            // NCS patched for predictable order
            ordered-by user;
            tailf:cli-suppress-mode;
            tailf:cli-range-list-syntax;
            key "id";
            leaf id {
              type string;
            }
            container timers {
              extreme-xos:replace-delete-output "un(.* server-timeout).*(quiet-period).*(supp-resp-timeout).* :: $1 30 $2 60 $3 30";
              leaf server-timeout {
                type string;
                // NCS drop default statement
              }
              leaf quiet-period {
                type string;
                // NCS drop default statement
              }
              leaf supp-resp-timeout {
                type string;
                // NCS drop default statement
              }
            }
          }
        }
        list ports {
          // NCS patched for predictable order
          ordered-by user;
          extreme-xos:trim-delete-if-match "unconfigure netlogin ports \\S+";
          tailf:cli-suppress-mode;
          tailf:cli-range-list-syntax;
          key "id";
          leaf id {
            type string;
          }
          leaf mode {
            type string;
          }
        }
        container authentication {
          leaf protocol-order {
            // NCS drop tailf-common:cli-diff-set-after statement
            extreme-xos:replace-delete-output "un(.*) :: $1 dot1x web-based mac cep";
            type string;
          }
        }
        leaf vlan {
          // NCS drop tailf-common:cli-diff-set-after statement
          // NCS drop tailf-common:cli-diff-delete-before statement
          type string;
        }
      }
      container policy {
        leaf rule-model {
          // NCS drop tailf-common:cli-diff-delete-after statement
          // NCS drop tailf-common:cli-diff-set-before statement
          extreme-xos:replace-delete-output "un(.*) :: $1 hierarchical";
          type string;
          // NCS drop default statement
        }
        container slices {
          leaf tci-overwrite {
            // NCS drop tailf-common:cli-diff-set-before statement
            extreme-xos:replace-delete-output "un(.*) :: $1 4";
            type string;
            // NCS drop default statement
          }
          leaf shared {
            // NCS drop tailf-common:cli-diff-delete-before statement
            // NCS drop tailf-common:cli-diff-set-before statement
            extreme-xos:replace-delete-output "un(.*) :: $1 0";
            type string;
            // NCS drop default statement
          }
        }
        container maptable {
          leaf response {
            type string;
          }
        }
        container vlanauthorization {
          leaf enable {
            extreme-xos:replace-delete-output "un(.*) :: $1 disable";
            type empty;
          }
        }
        list profile {
          // NCS patched for predictable order
          ordered-by user;
          tailf:cli-suppress-mode;
          key "index";
          leaf index {
            type string;
          }
          leaf name {
            type string;
          }
          leaf access-list {
            type string;
          }
          leaf pvid-status {
            type string;
          }
          leaf pvid {
            type string;
          }
          leaf web-redirect {
            type string;
          }
        }
        container captive-portal {
          leaf-list listening {
            // NCS patched for predictable order
            ordered-by user;
            type string;
          }
          list web-redirect {
            // NCS patched for predictable order
            ordered-by user;
            tailf:cli-suppress-mode;
            key "index server";
            leaf index {
              type string;
            }
            leaf server {
              type string;
            }
            leaf url {
              type string;
            }
            leaf status {
              tailf:cli-drop-node-name;
              type string;
            }
          }
        }
      }
      list stpd {
        // NCS patched for predictable order
        ordered-by user;
        tailf:cli-suppress-mode;
        // NCS drop tailf-common:cli-diff-create-after statement
        // NCS drop tailf-common:cli-diff-delete-before statement
        extreme-xos:trim-delete-if-match "unconfigure.*mode dot1d.*";
        key "name";
        leaf name {
          type string;
        }
        container ports {
          container edge-safeguard {
            uses ncs_compliance_template_ports-enable-grouping;
          }
          container bpdu-restrict {
            uses ncs_compliance_template_ports-enable-grouping;
          }
          list link-type {
            // NCS patched for predictable order
            ordered-by user;
            tailf:cli-suppress-mode;
            tailf:cli-range-list-syntax;
            // NCS drop tailf-common:cli-diff-create-after statement
            // NCS drop tailf-common:cli-diff-delete-before statement
            // NCS drop tailf-common:cli-diff-create-after statement
            // NCS drop tailf-common:cli-diff-delete-before statement
            key "ports";
            leaf ports {
              type string;
            }
            leaf edge {
              type empty;
            }
          }
        }
        list add {
          // NCS patched for predictable order
          ordered-by user;
          tailf:cli-suppress-mode;
          key "vlan";
          leaf vlan {
            type string;
          }
          leaf-list ports {
            // NCS patched for predictable order
            ordered-by user;
            // NCS drop tailf-common:cli-diff-set-after statement
            // NCS drop tailf-common:cli-diff-delete-before statement
            tailf:cli-range-list-syntax;
            type string;
          }
          leaf dot1d {
            type empty;
          }
        }
      }
      container cdp {
        list voip-vlan {
          // NCS patched for predictable order
          ordered-by user;
          extreme-xos:replace-delete-output "un(configure cdp voip-vlan) \\S+ (.*) :: $1 none $2";
          tailf:cli-suppress-mode;
          // NCS drop tailf-common:cli-diff-set-after statement
          // NCS drop tailf-common:cli-diff-delete-before statement
          key "vlan_name";
          leaf vlan_name {
            type string;
          }
          uses ncs_compliance_template_port-list-grouping;
        }
      }
      container lldp {
        list ports {
          // NCS patched for predictable order
          ordered-by user;
          // NCS drop tailf-common:cli-diff-set-after statement
          // NCS drop tailf-common:cli-diff-delete-before statement
          tailf:cli-suppress-mode;
          tailf:cli-range-list-syntax;
          key "id";
          leaf id {
            type string;
          }
          container advertise {
            leaf port-description {
              type empty;
            }
            leaf system-capabilities {
              type empty;
            }
            leaf management-address {
              type empty;
            }
          }
        }
      }
      container inline-power {
        container detection {
          list portlist {
            // NCS patched for predictable order
            ordered-by user;
            tailf:cli-drop-node-name;
            // NCS drop tailf-common:cli-diff-set-after statement
            // NCS drop tailf-common:cli-diff-delete-before statement
            tailf:cli-suppress-mode;
            tailf:cli-range-list-syntax;
            key "ports";
            leaf ports {
              type string;
            }
            leaf "legacy-and-802.3af" {
              type string;
            }
          }
        }
      }
    }
    container enable {
      extreme-xos:no-to-disable;
      container snmp {
        container access {
          presence "true";
          leaf snmp-v1v2c {
            type empty;
          }
          leaf snmpv3 {
            type empty;
          }
        }
        container traps {
          leaf fdb {
            type string;
          }
          container configuration {
            leaf change {
              type empty;
            }
            leaf save {
              type empty;
            }
          }
        }
      }
      leaf ssh2 {
        type empty;
      }
      leaf cli-config-logging {
        type empty;
      }
      leaf tacacs {
        type empty;
      }
      leaf tacacs-accounting {
        type empty;
      }
      leaf tacacs-authorization {
        type empty;
      }
      leaf sntp-client {
        type empty;
      }
      container log {
        leaf debug-mode {
          type empty;
        }
        container target {
          list syslog {
            // NCS patched for predictable order
            ordered-by user;
            // NCS drop tailf-common:cli-diff-create-after statement
            // NCS drop tailf-common:cli-diff-delete-before statement
            tailf:cli-suppress-mode;
            key "ipPort vr local";
            leaf ipPort {
              type string;
            }
            leaf vr {
              type string;
            }
            leaf local {
              tailf:cli-drop-node-name;
              type string;
            }
          }
          leaf-list upm {
            // NCS patched for predictable order
            ordered-by user;
            // NCS drop tailf-common:cli-diff-create-after statement
            // NCS drop tailf-common:cli-diff-delete-before statement
            // NCS drop tailf-common:cli-diff-modify-before statement
            type string;
          }
        }
      }
      container cli {
        leaf config-logging {
          type empty;
        }
      }
      container loopback-mode {
        list vlan {
          // NCS patched for predictable order
          ordered-by user;
          // NCS drop tailf-common:cli-diff-set-after statement
          // NCS drop tailf-common:cli-diff-delete-before statement
          tailf:cli-suppress-mode;
          key "id";
          leaf id {
            type string;
          }
        }
      }
      container ipforwarding {
        list vlan {
          // NCS patched for predictable order
          ordered-by user;
          tailf:cli-suppress-mode;
          // NCS drop tailf-common:cli-diff-set-after statement
          // NCS drop tailf-common:cli-diff-delete-before statement
          // NCS drop tailf-common:cli-diff-set-after statement
          // NCS drop tailf-common:cli-diff-delete-before statement
          key "id";
          leaf id {
            type string;
          }
        }
      }
      container diffserv {
        uses ncs_compliance_template_exam-grouping;
      }
      container radius {
        leaf netlogin {
          type empty;
        }
        leaf dynamic-authorization {
          type empty;
        }
      }
      list stpd {
        // NCS patched for predictable order
        ordered-by user;
        tailf:cli-suppress-mode;
        // NCS drop tailf-common:cli-diff-set-after statement
        // NCS drop tailf-common:cli-diff-delete-before statement
        key "name";
        leaf name {
          type string;
        }
        container auto-bind {
          // NCS expand uses statement
          leaf-list vlan {
            // NCS patched for predictable order
            ordered-by user;
            // NCS drop tailf-common:cli-diff-set-after statement
            // NCS drop tailf-common:cli-diff-delete-before statement
            type string;
            // NCS drop tailf-common:cli-diff-delete-after statement
          }
        }
      }
      container netlogin {
        list ports {
          // NCS patched for predictable order
          ordered-by user;
          // NCS drop tailf-common:cli-diff-set-after statement
          // NCS drop tailf-common:cli-diff-delete-before statement
          tailf:cli-suppress-mode;
          tailf:cli-range-list-syntax;
          key "id";
          leaf id {
            type string;
          }
          uses ncs_compliance_template_netlogin-authprotocol-grouping;
        }
        container dot1x-max {
          tailf:cli-drop-node-name;
          // NCS expand uses statement
          leaf dot1x {
            type empty;
            // NCS drop tailf-common:cli-diff-set-after statement
            // NCS drop tailf-common:cli-diff-delete-before statement
          }
          leaf mac {
            type empty;
            // NCS drop tailf-common:cli-diff-set-after statement
            // NCS drop tailf-common:cli-diff-delete-before statement
          }
          leaf web-based {
            type empty;
            // NCS drop tailf-common:cli-diff-set-after statement
            // NCS drop tailf-common:cli-diff-delete-before statement
          }
        }
      }
      leaf policy {
        type empty;
      }
      container cdp {
        uses ncs_compliance_template_port-list-grouping;
      }
      container ip-security {
        container dhcp-snooping {
          list vlan {
            // NCS patched for predictable order
            ordered-by user;
            // NCS drop tailf-common:cli-diff-set-after statement
            // NCS drop tailf-common:cli-diff-delete-before statement
            // NCS drop tailf-common:cli-diff-set-after statement
            // NCS drop tailf-common:cli-diff-delete-before statement
            tailf:cli-suppress-mode;
            key "id";
            leaf id {
              type string;
            }
            list ports {
              // NCS patched for predictable order
              ordered-by user;
              // NCS drop tailf-common:cli-diff-set-after statement
              // NCS drop tailf-common:cli-diff-delete-before statement
              // NCS drop tailf-common:cli-diff-set-after statement
              // NCS drop tailf-common:cli-diff-delete-before statement
              // NCS drop tailf-common:cli-diff-delete-before statement
              tailf:cli-suppress-mode;
              tailf:cli-range-list-syntax;
              key "id";
              leaf id {
                type string;
              }
              leaf violation-action {
                type string;
              }
            }
          }
        }
      }
    }
    container disable {
      extreme-xos:no-to-disable;
      leaf telnet {
        type empty;
      }
      list stpd {
        // NCS patched for predictable order
        ordered-by user;
        tailf:cli-suppress-mode;
        key "stpd_name";
        leaf stpd_name {
          type string;
        }
      }
      container snmp {
        container traps {
          container port-up-down {
            leaf-list port {
              // NCS patched for predictable order
              ordered-by user;
              tailf:cli-range-list-syntax;
              type string;
            }
          }
        }
      }
      container dot1p {
        uses ncs_compliance_template_exam-grouping;
      }
      container edp {
        uses ncs_compliance_template_port-list-grouping;
      }
    }
  }

  extension remove-before-change {
    cli:direction "to-device";
    cli:state "post-match";
    cli:java-callback-method "com.tailf.packages.ned.extremexos.ExtremeXosCliExtensions.removeBeforeChange";
  }

  extension redeploy-access-profile-at-acl-modify {
    cli:direction "to-device";
    cli:state "post-match";
    cli:java-callback-method "com.tailf.packages.ned.extremexos.ExtremeXosCliExtensions.redeployAccesProfileAtAclModify";
  }

  extension quoted-string {
    cli:direction "to-device";
    cli:state "post-match";
    cli:java-callback-method "com.tailf.packages.ned.extremexos.ExtremeXosCliExtensions.quotedString";
  }

  extension no-to-disable {
    cli:direction "both";
    cli:state "pre-match|post-match";
    cli:java-callback-method "com.tailf.packages.ned.extremexos.ExtremeXosCliExtensions.noToDisable";
  }

  extension delete-with {
    cli:direction "to-device";
    cli:state "post-match";
    cli:java-callback-method "com.tailf.packages.ned.extremexos.ExtremeXosCliExtensions.deleteWith";
    argument value;
  }

  extension trim-delete-if-match {
    cli:direction "to-device";
    cli:state "post-match";
    cli:java-callback-method "com.tailf.packages.ned.extremexos.ExtremeXosCliExtensions.deleteWith";
    argument value;
  }

  extension replace-delete-output {
    cli:direction "to-device";
    cli:state "post-match";
    cli:java-callback-method "com.tailf.packages.ned.extremexos.ExtremeXosCliExtensions.deleteWith";
    argument value;
  }

  extension send-secret {
    cli:direction "to-device";
    cli:state "post-match";
    cli:java-callback-method "com.tailf.packages.ned.extremexos.ExtremeXosCliExtensions.sendSecret";
  }

  extension multi-line-banner {
    cli:direction "to-device";
    cli:state "post-match";
    cli:java-callback-method "com.tailf.packages.ned.extremexos.ExtremeXosCliExtensions.multiLineBanner";
  }

  extension replace-input {
    cli:direction "from-device";
    cli:state "pre-match";
    cli:java-callback-method "com.tailf.packages.ned.extremexos.ExtremeXosCliExtensions.replaceInput";
  }

  extension accounts-password {
    cli:direction "to-device";
    cli:state "post-match";
    cli:java-callback-method "com.tailf.packages.ned.extremexos.ExtremeXosCliExtensions.accountsPwd";
  }

  extension upm-list-out {
    cli:direction "both";
    cli:state "multi-line";
    cli:java-callback-method "com.tailf.packages.ned.extremexos.ExtremeXosCliExtensions.upmListOut";
  }
}
