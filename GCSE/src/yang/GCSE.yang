module GCSE {
    namespace "http://com/example/GCSE";
    prefix GCSE;

    import ietf-inet-types {
        prefix inet;
    }
    import tailf-ncs {
        prefix ncs;
    }
    import tailf-common {
        prefix tailf;
    }

    list GCSE {
        key id;
        uses ncs:service-data;
        ncs:servicepoint "GCSE";
        leaf id {
            tailf:info "Access Service ID";
            type string;
        }
        leaf-list device {
            tailf:info "Devices";
            type leafref {
                path "/ncs:devices/ncs:device/ncs:name";
            }
        }
        container transport-information {
            tailf:info "Transport Information";
            container options {
                tailf:info "Transport Options";
                container settings {
                    tailf:info "Transport Settings";
                    container equipment-information {
                        tailf:info "Equipment Information";
                        leaf-list node-type {
                            type string;
                        }
                        container PE {
                            when "../node-type = 'PE'";
                            leaf hostname {
                                tailf:info "Hostname";
                                type string;
                            }
                            leaf vendor {
                                tailf:info "Vendor";
                                type string;
                            }
                            leaf model {
                                tailf:info "Model";
                                type string;
                            }
                            leaf software {
                                tailf:info "Software";
                                type string;
                            }
                            leaf interface {
                                type string;
                            }
                        }
                        container CE {
                            when "../node-type = 'CE'";
                            leaf hostname {
                                tailf:info "Hostname";
                                type string;
                            }
                            leaf vendor {
                                tailf:info "Vendor";
                                type string;
                            }
                            leaf model {
                                tailf:info "Model";
                                type string;
                            }
                            leaf software {
                                tailf:info "Software";
                                type string;
                            }
                            leaf interface {
                                type string;
                            }
                        }
                    }
                    container circuit-information {
                        tailf:info "Circuit Information";
                        container fttx {
                            leaf encapsulation {
                                type enumeration {
                                    enum dot1q;
                                }
                            }
                            leaf cvlan {
                                type string;
                            }
                        }
                    }
                }
            }
        }
        container service-information {
            tailf:info "Service Information";
            container bandwidth {
                leaf capacity {
                    tailf:info "Bandwidth Capacity";
                    type int8;
                }
                leaf unit {
                    tailf:info "Unit";
                    type string;
                }
            }
            container network-options {
                leaf asn {
                    tailf:info "Network ASN";
                    type string;
                }
                leaf protocol {
                    tailf:info "Network Protocol";
                    type enumeration {
                        enum ip;
                        enum tldp;
                        enum vpls;
                        enum vpnv4;
                    }
                }
                choice conditional {
                    case vpnv4 {
                        when "../network-options/protocol = 'vpnv4'";
                        container vpnv4 {
                            leaf vrf {
                                tailf:info "VRF Name";
                                type string;
                            }
                            leaf route-distinguisher {
                                tailf:info "Route Distinguisher";
                                type string;
                            }
                            leaf-list route-target-import {
                                tailf:info "Route Target Import Community";
                                type string;
                            }
                            leaf-list route-target-export {
                                tailf:info "Route Target Import Community";
                                type string;
                            }
                        }
                    }
                }
            }
            container service-options {
                container ip-settings {
                    tailf:info "IP Settings";
                    list ip {
                        key address-family;
                        leaf address-family {
                            tailf:info "IP Version";
                            type enumeration {
                                enum ipv4;
                                enum ipv6;
                            }
                        }
                        choice version {
                            case v4 {
                                when "../ip/address-family = 'ipv4'";
                                list network {
                                    key "pfx";
                                    leaf pfx {
                                        tailf:info "IPv4 Network Prefix";
                                        type string;
                                    }
                                    leaf role {
                                        tailf:info "Primary/Secondary";
                                        type enumeration {
                                          enum primary;
                                          enum secondary;
                                        }
                                    }
                                    list hosts {
                                        tailf:info "Host Table";
                                        key "node";
                                        leaf node {
                                          tailf:info "Hostname";
                                          type string;
                                        }
                                        leaf address {
                                          tailf:info "Address";
                                          type string;
                                        }
                                        leaf subnet-mask {
                                          tailf:info "Subnet Mask";
                                          type string;
                                        }
                                    }
                                }
                            }
                        }
                    }
                    list routing {
                        key protocol;
                        leaf protocol {
                            type enumeration {
                                enum bgp;
                                enum static;
                            }
                        }
                        choice routing-protocol {
                            case dymaic {
                                when "../routing/protocol = 'bgp'";
                                list network {
                                    key pfx;
                                    leaf pfx {
                                        tailf:info "IPv4 Network Prefix";
                                        type string;
                                    }
                                    list peers {
                                        key "node";
                                        leaf node {
                                            tailf:info "Hostname";
                                            type string;
                                        }
                                        leaf update-source {
                                            tailf:info "Local Update Source";
                                            type string;
                                        }
                                        leaf local-asn {
                                            tailf:info "Local ASN";
                                            type string;
                                        }
                                        leaf remote-address {
                                            tailf:info "Remote Address";
                                            type string;
                                        }
                                        leaf remote-asn {
                                            tailf:info "Remote ASN";
                                            type string;
                                        }
                                        leaf afi {
                                            tailf:info "AFI";
                                            type enumeration {
                                                enum ipv4;
                                            }
                                        }
                                        leaf route-policy-in {
                                            tailf:info "Route Policy In";
                                            type string;
                                        }
                                        leaf route-policy-out {
                                            tailf:info "Route Policy Out";
                                            type string;
                                        }
                                    }
                                }
                            }
                            case static {
                                when "../routing/protocol = 'static'";
                                container static {
                                    list entry {
                                        key "node";
                                        leaf node {
                                            tailf:info "Hostname";
                                            type string;
                                        }
                                        leaf address {
                                            tailf:info "Network";
                                            type string;
                                        }
                                        leaf subnet-mask {
                                            tailf:info "Subnet-Mask";
                                            type string;
                                        }
                                        leaf next-hop {
                                            tailf:info "Next-Hop";
                                            type string;
                                        }
                                    }
                                }
                            }
                        }
                    }
                }
            }
        }
    }
}
