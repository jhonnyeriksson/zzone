module GC {
  namespace "http://com/example/GC";
  prefix GC;

  import ietf-inet-types {
    prefix inet;
  }
  import tailf-ncs {
    prefix ncs;
  }
  import tailf-common {
    prefix tailf;
  }
  list GC {
    key id;
    uses ncs:service-data;
    ncs:servicepoint "GC";
    leaf id {
      tailf:info "Access Service ID";
      type string;
    }
    leaf-list devices {
      type leafref {
        path "/ncs:devices/ncs:device/ncs:name";
      }
    }
    container transport-information {
      container options {
        container settings {
          container equipment-information {
            list PE {
              key "node";
              leaf node {
                  type string;
              }
              leaf loopback {
                  type string;
              }
              leaf vendor {
                  type string;
              }
              leaf model {
                  type string;
              }
              leaf software {
                  type string;
              }
              list service-interface {
                key "interface";
                leaf interface {
                  type string;
                }
                leaf mode {
                  type enumeration {
                    enum tagged;
                    enum untagged;
                  }
                }
              }
            }
            list ACCESS {
              key "node";
              leaf node {
                type string;
              }
              leaf vendor {
                type string;
              }
              leaf model {
                type string;
              }
              list service-interface {
                key "interface";
                leaf interface {
                  type string;
                }
                leaf mode {
                  type enumeration {
                    enum tagged;
                    enum untagged;
                  }
                }
              }
            }
            list CPE {
              key "node";
              leaf node {
                  type string;
              }
              leaf loopback {
                  type string;
              }
              leaf vendor {
                  type string;
              }
              leaf model {
                  type string;
              }
              leaf software {
                  type string;
              }
              list service-interface {
                key "interface";
                leaf interface {
                  type string;
                }
                leaf mode {
                  type enumeration {
                    enum tagged;
                    enum untagged;
                  }
                }
              }
            }
          }
          container circuit-information {
            container fttx {
              leaf encapsulation {
                  type enumeration {
                      enum dot1q;
                  }
              }
              container vlan {
                when "../encapsulation = 'dot1q'";
                leaf cvlan-id {
                  type string;
                }
                leaf cvlan-name {
                  type string;
                }
              }
            }
          }
        }
      }
    }
    container service-information {
      container addon {
        container qos {
          leaf active {
            type boolean;
          }
          leaf profile {
            type enumeration {
              enum basic;
            }
          }
        }
      }
      container network-options {
        leaf asn {
          type string;
        }
        leaf network-protocol {
          type enumeration {
            enum ipv4;
            enum ipv6;
            enum tldp;
            enum vpls;
            enum vpnv4;
            enum vpnv6;
          }
        }
        choice conditional {
          case vpnv4 {
            container vpnv4 {
              when "../network-protocol = 'vpnv4'";
              leaf vrf {
                type string;
              }
              leaf rd {
                type string;
              }
              leaf route-target-import {
                type string;
              }
              leaf route-target-export {
                type string;
              }
            }
          }
        }
      }
      container service-options {
        container ip-settings {
          container ip {
            leaf address-family {
              type enumeration {
                enum ipv4;
              }
            }
            choice version {
              case ipv4 {
                container ipv4 {
                  when "../address-family = 'ipv4'";
                  leaf network {
                    type string;
                  }
                  list hosts {
                    key "node";
                    leaf node {
                      type string;
                    }
                    leaf address {
                      type string;
                    }
                    leaf subnet-mask {
                      type string;
                    }
                  }
                }
              }
            }
          }
          container routing {
            leaf routing-protocol {
              type enumeration {
                enum static;
                enum bgp;
              }
            }
            choice protocol {
              case manual {
                container static {
                  when "../routing-protocol = 'static'";
                  list entry {
                    key "node";
                    leaf node {
                      type string;
                    }
                    leaf network {
                      type string;
                    }
                    leaf subnet-mask {
                      type string;
                    }
                    leaf next-hop {
                      type string;
                    }
                  }
                }
              }
              case dynamic {
                container bgp {
                  when "../routing-protocol = 'bgp'";
                  list peer {
                    key "node";
                    leaf node {
                      type string;
                    }
                    leaf local-asn {
                      type string;
                    }
                    leaf update-source {
                      type string;
                    }
                    leaf remote-address {
                      type string;
                    }
                    leaf remote-asn {
                      type string;
                    }
                    leaf route-policy-in {
                      type string;
                    }
                    leaf route-policy-out {
                      type string;
                    }
                  }
                }
              }
            }
          }
        }
      }
    }
  }
}
