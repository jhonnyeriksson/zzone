module CFS {

  namespace "http://example.com/CFS";
  prefix CFS;

  import tailf-common {
    prefix tailf;
  }
  import tailf-ncs {
    prefix ncs;
  }

  description
    "Customer-facing service: request loopbacks for a device.";

  revision 2016-01-01 {
    description
      "Initial revision.";
  }

  list CFS {
    description "CFS that triggers an RFS to create loopbacks";

    key name;
    leaf name {
      tailf:info "Unique service id";
      tailf:cli-allow-range;
      type string;
    }

    uses ncs:service-data;
    ncs:servicepoint CFS-servicepoint;

    leaf hostname {
      tailf:info "Logical hostname; CFS maps this to a real device";
      mandatory true;
      type enumeration {
        enum router1 {
          description "Maps to device XRv1";
        }
        enum router2 {
          description "Maps to device XRv2";
        }
      }
    }
  }
}
